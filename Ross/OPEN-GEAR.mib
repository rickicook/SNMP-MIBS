OPEN-GEAR-MIB DEFINITIONS ::= BEGIN

--
-- Top-level infrastructure of the Open-Gear MIB tree
--

IMPORTS
  rossVideo FROM ROSS-VIDEO-MIB

  MODULE-IDENTITY FROM SNMPv2-SMI;

openGear MODULE-IDENTITY
  LAST-UPDATED "200703070000Z"
  ORGANIZATION "www.rossvideo.com"
  CONTACT-INFO
    "postal:   Ross Video Limited
               8 John St. P.O. Box 220
               Iroquois ON K0E 1K0
               Canada

    email:    support@rossvideo.com"
  DESCRIPTION
    "Top-level infrastructure of the Open-Gear MIB tree"
  REVISION     "200703070000Z"
  DESCRIPTION
    "First draft"
    ::= { rossVideo 1 }

--
--  Open Gear management objects
--
openGearObjects              OBJECT IDENTIFIER ::= { openGear 1 }

END
