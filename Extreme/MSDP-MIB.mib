-- extracted from draft-ietf-msdp-mib-01.txt
-- at Mon Nov 15 17:10:40 1999

MSDP-MIB DEFINITIONS ::= BEGIN

IMPORTS
    MODULE-IDENTITY, OBJECT-TYPE, NOTIFICATION-TYPE,
    experimental, Counter32, Gauge32, IpAddress, TimeTicks
        FROM SNMPv2-SMI
    RowStatus, TruthValue
        FROM SNMPv2-TC
    MODULE-COMPLIANCE, OBJECT-GROUP, NOTIFICATION-GROUP
        FROM SNMPv2-CONF;

msdpMIB MODULE-IDENTITY
    LAST-UPDATED "9904070000Z"
    ORGANIZATION "IETF MSDP Working Group"
    CONTACT-INFO
            " Bill Fenner
              75 Willow Road
              Menlo Park, CA  94025
              Phone: +1 650 867 6073
              E-mail: fenner@research.att.com

              Dave Thaler
              One Microsoft Way
              Redmond, WA  98052
              Phone: +1 425 703 8835
              Email: dthaler@microsoft.com"
    DESCRIPTION
            "An experimental MIB module for MSDP Management."
    ::= { experimental 92 }

msdpMIBobjects OBJECT IDENTIFIER ::= { msdpMIB 1 }

msdp           OBJECT IDENTIFIER ::= { msdpMIBobjects 1 }

msdpEnabled OBJECT-TYPE
    SYNTAX     TruthValue
    MAX-ACCESS read-write
    STATUS     current
    DESCRIPTION
            "The state of MSDP on this MSDP speaker - globally
            enabled or disabled."
    ::= { msdp 1 }

msdpCacheLifetime OBJECT-TYPE
    SYNTAX     TimeTicks
    MAX-ACCESS read-write
    STATUS     current
    DESCRIPTION
            "The lifetime given to SA cache entries when created
            or refreshed.  A value of 0 means no SA caching is
            done by this MSDP speaker."
    ::= { msdp 2 }

msdpNumSACacheEntries OBJECT-TYPE
    SYNTAX     Gauge32
    MAX-ACCESS read-only
    STATUS     current
    DESCRIPTION
            "The total number of entries in the SA Cache table."
    ::= { msdp 3 }

msdpSendRequestsTo OBJECT-TYPE
    SYNTAX     IpAddress
    MAX-ACCESS read-write
    STATUS     current
    DESCRIPTION
            "The peer to whom to send MSDP SA Request messages
            when not performing SA Caching.  This must be an
            address listed in the Peer table, or 0.0.0.0 to
            indicate that Request messages are not to be sent."
    ::= { msdp 4 }

---
--- The MSDP Peer table
---

msdpPeerTable OBJECT-TYPE
    SYNTAX     SEQUENCE OF MsdpPeerEntry
    MAX-ACCESS not-accessible
    STATUS     current
    DESCRIPTION
            "The (conceptual) table listing the MSDP speaker's
            peers."
    ::= { msdp 5 }

msdpPeerEntry OBJECT-TYPE
    SYNTAX     MsdpPeerEntry
    MAX-ACCESS not-accessible
    STATUS     current
    DESCRIPTION
            "An entry (conceptual row) representing an MSDP peer."
    INDEX      { msdpPeerRemoteAddress }
    ::= { msdpPeerTable 1 }

MsdpPeerEntry ::= SEQUENCE {
    msdpPeerRemoteAddress             IpAddress,  -- index
    msdpPeerConfigMethod              INTEGER,    -- read-only objects:
    msdpPeerState                     INTEGER,
    msdpPeerRPFFailures               Counter32,
    msdpPeerInSAs                     Counter32,
    msdpPeerOutSAs                    Counter32,
    msdpPeerInSARequests              Counter32,
    msdpPeerOutSARequests             Counter32,
    msdpPeerInSAResponses             Counter32,
    msdpPeerOutSAResponses            Counter32,
    msdpPeerInControlMessages         Counter32,
    msdpPeerOutControlMessages        Counter32,
    msdpPeerInDataPackets             Counter32,
    msdpPeerOutDataPackets            Counter32,
    msdpPeerFsmEstablishedTransitions Counter32,
    msdpPeerFsmEstablishedTime        Gauge32,
    msdpPeerInMessageElapsedTime      Gauge32,
    msdpPeerLocalAddress              IpAddress,  -- configuration objects:
    msdpPeerSAAdvPeriod               INTEGER,
    msdpPeerConnectRetryInterval      INTEGER,
    msdpPeerHoldTimeConfigured        INTEGER,
    msdpPeerKeepAliveConfigured       INTEGER,
    msdpPeerDataTtl                   INTEGER,
    msdpPeerProcessRequestsFrom       TruthValue,
    msdpPeerStatus                    RowStatus
}

msdpPeerRemoteAddress OBJECT-TYPE
    SYNTAX     IpAddress
    MAX-ACCESS not-accessible
    STATUS     current
    DESCRIPTION
            "The address of the remote MSDP peer."
    ::= { msdpPeerEntry 1 }

msdpPeerConfigMethod OBJECT-TYPE
    SYNTAX     INTEGER { manual(1), pimHello(2), bgpCapability(3) }
    MAX-ACCESS read-only
    STATUS     current
    DESCRIPTION
            "How this peer was configured; manually (1) or via one
            of the automatic mechanisms described in the MSDP
            spec."
    ::= { msdpPeerEntry 2 }

msdpPeerState OBJECT-TYPE
    SYNTAX     INTEGER { idle(1),
                         connect(2),
                         active(3),
                         established(4)
                       }
    MAX-ACCESS read-only
    STATUS     current
    DESCRIPTION
            "The state of the MSDP TCP connection with this peer."
    ::= { msdpPeerEntry 3 }

msdpPeerRPFFailures OBJECT-TYPE
    SYNTAX     Counter32
    MAX-ACCESS read-only
    STATUS     current
    DESCRIPTION
            "The number of RPF failures on SA messages received
            from this peer."
    ::= { msdpPeerEntry 4 }

msdpPeerInSAs OBJECT-TYPE
    SYNTAX     Counter32
    MAX-ACCESS read-only
    STATUS     current
    DESCRIPTION
            "The number of MSDP SA messages received on this
            connection.  This object should be initialized to zero
            when the connection is established."
    ::= { msdpPeerEntry 5 }

msdpPeerOutSAs OBJECT-TYPE
    SYNTAX     Counter32
    MAX-ACCESS read-only
    STATUS     current
    DESCRIPTION
            "The number of MSDP SA messages transmitted on this
            connection.  This object should be initialized to zero
            when the connection is established."
    ::= { msdpPeerEntry 6 }

msdpPeerInSARequests OBJECT-TYPE
    SYNTAX     Counter32
    MAX-ACCESS read-only
    STATUS     current
    DESCRIPTION
            "The number of MSDP SA-Request messages received on
            this connection.  This object should be initialized to
            zero when the connection is established."
    ::= { msdpPeerEntry 7 }

msdpPeerOutSARequests OBJECT-TYPE
    SYNTAX     Counter32
    MAX-ACCESS read-only
    STATUS     current
    DESCRIPTION
            "The number of MSDP SA-Request messages transmitted on
            this connection.  This object should be initialized to
            zero when the connection is established."
    ::= { msdpPeerEntry 8 }

msdpPeerInSAResponses OBJECT-TYPE
    SYNTAX     Counter32
    MAX-ACCESS read-only
    STATUS     current
    DESCRIPTION
            "The number of MSDP SA-Response messages received on
            this connection.  This object should be initialized to
            zero when the connection is established."
    ::= { msdpPeerEntry 9 }

msdpPeerOutSAResponses OBJECT-TYPE
    SYNTAX     Counter32
    MAX-ACCESS read-only
    STATUS     current
    DESCRIPTION
            "The number of MSDP SA Response messages transmitted
            on this TCP connection.  This object should be
            initialized to zero when the connection is
            established."
    ::= { msdpPeerEntry 10 }

msdpPeerInControlMessages OBJECT-TYPE
    SYNTAX     Counter32
    MAX-ACCESS read-only
    STATUS     current
    DESCRIPTION
            "The total number of MSDP messages received on this
            TCP connection.  This object should be initialized to
            zero when the connection is established."
    ::= { msdpPeerEntry 11 }

msdpPeerOutControlMessages OBJECT-TYPE
    SYNTAX     Counter32
    MAX-ACCESS read-only
    STATUS     current
    DESCRIPTION
            "The total number of MSDP messages transmitted on this
            TCP connection.  This object should be initialized to
            zero when the connection is established."
    ::= { msdpPeerEntry 12 }

msdpPeerInDataPackets OBJECT-TYPE
    SYNTAX     Counter32
    MAX-ACCESS read-only
    STATUS     current
    DESCRIPTION
            "The total number of encapsulated data packets
            received from this peer.  This object should be
            initialized to zero when the connection is
            established."
    ::= { msdpPeerEntry 13 }

msdpPeerOutDataPackets OBJECT-TYPE
    SYNTAX     Counter32
    MAX-ACCESS read-only
    STATUS     current
    DESCRIPTION
            "The total number of encapsulated data packets sent to
            this peer.  This object should be initialized to zero
            when the connection is established."
    ::= { msdpPeerEntry 14 }

msdpPeerFsmEstablishedTransitions OBJECT-TYPE
    SYNTAX     Counter32
    MAX-ACCESS read-only
    STATUS     current
    DESCRIPTION
            "The total number of times the MSDP FSM transitioned
            into the established state."
    ::= { msdpPeerEntry 15 }

msdpPeerFsmEstablishedTime OBJECT-TYPE
    SYNTAX     Gauge32
    UNITS      "seconds"
    MAX-ACCESS read-only
    STATUS     current
    DESCRIPTION
            "This timer indicates how long (in seconds) this peer
            has been in the Established state or how long since
            this peer was last in the Established state.  It is
            set to zero when a new peer is configured or the MSDP
            speaker is booted."
    ::= { msdpPeerEntry 16 }

msdpPeerInMessageElapsedTime OBJECT-TYPE
    SYNTAX     Gauge32
    UNITS      "seconds"
    MAX-ACCESS read-only
    STATUS     current
    DESCRIPTION
            "Elapsed time in seconds since the last MSDP message
            was received from the peer.  Each time
            msdpPeerInControlMessages is incremented, the value of
            this object is set to zero (0)."
    ::= { msdpPeerEntry 17 }

msdpPeerLocalAddress OBJECT-TYPE
    SYNTAX     IpAddress
    MAX-ACCESS read-create
    STATUS     current
    DESCRIPTION
            "The local IP address of this entry's MSDP
            connection."
    ::= { msdpPeerEntry 18 }

msdpPeerSAAdvPeriod OBJECT-TYPE
    SYNTAX     INTEGER(1..2147483647)
    UNITS      "seconds"
    MAX-ACCESS read-create
    STATUS     current
    DESCRIPTION
            "Time interval in seconds for the
            MinSAAdvertisementInterval MSDP timer."
    DEFVAL  { 60 }
    ::= { msdpPeerEntry 19 }

msdpPeerConnectRetryInterval OBJECT-TYPE
    SYNTAX     INTEGER (1..65535)
    UNITS      "seconds"
    MAX-ACCESS read-create
    STATUS     current
    DESCRIPTION
            "Time interval in seconds for the ConnectRetry timer."
    DEFVAL { 120 }
    ::= { msdpPeerEntry 20 }

msdpPeerHoldTimeConfigured OBJECT-TYPE
    SYNTAX     INTEGER  ( 0 | 3..65535 )
    UNITS      "seconds"
    MAX-ACCESS read-create
    STATUS     current
    DESCRIPTION
            "Time interval in seconds for the Hold Timer
            configured for this MSDP speaker with this peer."
    DEFVAL { 90 }
    ::= { msdpPeerEntry 21 }

msdpPeerKeepAliveConfigured OBJECT-TYPE
    SYNTAX     INTEGER ( 0 | 1..21845 )
    UNITS      "seconds"
    MAX-ACCESS read-create
    STATUS     current
    DESCRIPTION
            "Time interval in seconds for the KeepAlive timer
            configured for this MSDP speaker with this peer.  A
            reasonable maximum value for this timer would be
            configured to be one third of that of
            msdpPeerHoldTimeConfigured.  If the value of this
            object is zero (0), no periodic KEEPALIVE messages are
            sent to the peer after the MSDP connection has been
            established."
    DEFVAL { 30 }
    ::= { msdpPeerEntry 22 }

msdpPeerDataTtl OBJECT-TYPE
    SYNTAX     INTEGER (0..255)
    MAX-ACCESS read-create
    STATUS     current
    DESCRIPTION
            "The minimum TTL a packet is required to have before
            it may be forwarded using SA encapsulation to this
            peer."
    ::= { msdpPeerEntry 23 }

msdpPeerProcessRequestsFrom OBJECT-TYPE
    SYNTAX     TruthValue
    MAX-ACCESS read-create
    STATUS     current
    DESCRIPTION
            "This object indicates whether or not to process MSDP
            SA Request messages from this peer.  If True(1), MSDP
            SA Request messages from this peer are processed and
            replied to (if appropriate) with SA Response messages.
            If False(2), MSDP SA Request messages from this peer
            are silently ignored."
    ::= { msdpPeerEntry 24 }

msdpPeerStatus OBJECT-TYPE
    SYNTAX      RowStatus
    MAX-ACCESS  read-create
    STATUS      current
    DESCRIPTION
            "The RowStatus object by which peers can be added and
            deleted.  A transition to 'active' will cause the MSDP
            Start Event to be generated.  A transition out of the
            'active' state will cause the MSDP Stop Event to be
            generated.  Care should be used in providing write
            access to this object without adequate
            authentication."
    ::= { msdpPeerEntry 25 }

---
--- The MSDP Source-Active Cache table
---

msdpSACacheTable OBJECT-TYPE
    SYNTAX     SEQUENCE OF MsdpSACacheEntry
    MAX-ACCESS not-accessible
    STATUS     current
    DESCRIPTION
            "The (conceptual) table listing the MSDP SA
            advertisements currently in the MSDP speaker's cache."
    ::= { msdp 6 }

msdpSACacheEntry OBJECT-TYPE
    SYNTAX     MsdpSACacheEntry
    MAX-ACCESS not-accessible
    STATUS     current
    DESCRIPTION
            "An entry (conceptual row) representing an MSDP SA
            advert."
    INDEX      { msdpSACacheGroupAddr, msdpSACacheSourceAddr }
    ::= { msdpSACacheTable 1 }

MsdpSACacheEntry ::= SEQUENCE {
    msdpSACacheGroupAddr       IpAddress,
    msdpSACacheSourceAddr      IpAddress,
    msdpSACacheOriginRP        IpAddress,
    msdpSACachePeerLearnedFrom IpAddress,
    msdpSACacheRPFPeer         IpAddress,
    msdpSACacheInSAs           Counter32,
    msdpSACacheInDataPackets   Counter32,
    msdpSACacheUpTime          TimeTicks,
    msdpSACacheExpiryTime      TimeTicks,
    msdpSACacheStatus          RowStatus
}

msdpSACacheGroupAddr OBJECT-TYPE
    SYNTAX     IpAddress
    MAX-ACCESS not-accessible
    STATUS     current
    DESCRIPTION
            "The group address of the SA Cache entry."
    ::= { msdpSACacheEntry 1 }

msdpSACacheSourceAddr OBJECT-TYPE
    SYNTAX     IpAddress
    MAX-ACCESS not-accessible
    STATUS     current
    DESCRIPTION
            "The source address of the SA Cache entry."
    ::= { msdpSACacheEntry 2 }

msdpSACacheOriginRP OBJECT-TYPE
    SYNTAX     IpAddress
    MAX-ACCESS read-only
    STATUS     current
    DESCRIPTION
            "The address of the RP which originated the last SA
            message accepted for this entry."
    ::= { msdpSACacheEntry 3 }

msdpSACachePeerLearnedFrom OBJECT-TYPE
    SYNTAX     IpAddress
    MAX-ACCESS read-only
    STATUS     current
    DESCRIPTION
            "The peer from which this SA Cache entry was last
            accepted.  This address must correspond to the
            msdpPeerRemoteAddress value for a row in the MSDP Peer
            Table."
    ::= { msdpSACacheEntry 4 }

msdpSACacheRPFPeer OBJECT-TYPE
    SYNTAX     IpAddress
    MAX-ACCESS read-only
    STATUS     current
    DESCRIPTION
            "The peer from which an SA message corresponding to
            this cache entry would be accepted (i.e. the RPF peer
            for msdpSACacheOriginRP).  This may be different than
            msdpSACachePeerLearnedFrom if this entry was created
            by an MSDP SA-Response.  This address must correspond
            to the msdpPeerRemoteAddress value for a row in the
            MSDP Peer Table."
    ::= { msdpSACacheEntry 5 }

msdpSACacheInSAs OBJECT-TYPE
    SYNTAX     Counter32
    MAX-ACCESS read-only
    STATUS     current
    DESCRIPTION
            "The number of MSDP SA messages received relevant to
            this cache entry.  This object must be initialized to
            zero when creating a cache entry."
    ::= { msdpSACacheEntry 6 }

msdpSACacheInDataPackets OBJECT-TYPE
    SYNTAX     Counter32
    MAX-ACCESS read-only
    STATUS     current
    DESCRIPTION
            "The number of MSDP encapsulated data packets received
            relevant to this cache entry.  This object must be
            initialized to zero when creating a cache entry."
    ::= { msdpSACacheEntry 7 }

msdpSACacheUpTime OBJECT-TYPE
    SYNTAX     TimeTicks
    MAX-ACCESS read-only
    STATUS     current
    DESCRIPTION
            "The time since this entry was placed in the SA
            cache."
    ::= { msdpSACacheEntry 8 }

msdpSACacheExpiryTime OBJECT-TYPE
    SYNTAX     TimeTicks
    MAX-ACCESS read-only
    STATUS     current
    DESCRIPTION
            "The time remaining before this entry will expire from
            the SA cache."
    ::= { msdpSACacheEntry 9 }

msdpSACacheStatus OBJECT-TYPE
    SYNTAX     RowStatus
    MAX-ACCESS read-write
    STATUS     current
    DESCRIPTION
            "The status of this row in the table.  The only
            allowable actions are to retreive the status, which
            will be `active', or to set the status to `destroy' in
            order to remove this entry from the cache."
    ::= { msdpSACacheEntry 10 }

-- Traps

msdpTraps   OBJECT IDENTIFIER ::= { msdp 7 }

msdpEstablished NOTIFICATION-TYPE
    OBJECTS { msdpPeerFsmEstablishedTransitions }
    STATUS  current
    DESCRIPTION
            "The MSDP Established event is generated when the MSDP
            FSM enters the ESTABLISHED state."
    ::= { msdpTraps 1 }

msdpBackwardTransition NOTIFICATION-TYPE
    OBJECTS { msdpPeerState }
    STATUS  current
    DESCRIPTION
            "The MSDPBackwardTransition Event is generated when
            the MSDP FSM moves from a higher numbered state to a
            lower numbered state."
    ::= { msdpTraps 2 }

-- conformance information

msdpMIBConformance OBJECT IDENTIFIER ::= { msdp 8 }
msdpMIBCompliances OBJECT IDENTIFIER ::= { msdpMIBConformance 1 }
msdpMIBGroups      OBJECT IDENTIFIER ::= { msdpMIBConformance 2 }

-- compliance statements

msdpMIBCompliance MODULE-COMPLIANCE
   STATUS current
    DESCRIPTION
            "The compliance statement for entities which implement
            the MSDP MIB."
   MODULE  -- this module
   MANDATORY-GROUPS { msdpMIBGlobalsGroup }

       GROUP  msdpSACacheGroup
        DESCRIPTION
                "This group is mandatory if the MSDP speaker has
                the ability to cache SA messages."

   ::= { msdpMIBCompliances 1 }

-- units of conformance

msdpMIBGlobalsGroup OBJECT-GROUP
   OBJECTS { msdpEnabled, msdpSendRequestsTo }
   STATUS  current
    DESCRIPTION
            "A collection of objects providing information on
            global MSDP state."
   ::= { msdpMIBGroups 1 }

msdpMIBPeerGroup OBJECT-GROUP
   OBJECTS { msdpPeerConfigMethod, msdpPeerRPFFailures,
             msdpPeerState, msdpPeerInSAs, msdpPeerOutSAs,
             msdpPeerInSARequests, msdpPeerOutSARequests,
             msdpPeerInSAResponses, msdpPeerOutSAResponses,
             msdpPeerInControlMessages, msdpPeerOutControlMessages,
             msdpPeerInDataPackets, msdpPeerOutDataPackets,
             msdpPeerFsmEstablishedTransitions,
             msdpPeerFsmEstablishedTime,
             msdpPeerLocalAddress, msdpPeerSAAdvPeriod,
             msdpPeerConnectRetryInterval,
             msdpPeerHoldTimeConfigured,
             msdpPeerKeepAliveConfigured,
             msdpPeerInMessageElapsedTime,
        msdpPeerDataTtl,
        msdpPeerProcessRequestsFrom,
             msdpPeerStatus
           }
    STATUS  current
    DESCRIPTION
            "A collection of objects for managing MSDP peers."
    ::= { msdpMIBGroups 2 }

msdpSACacheGroup OBJECT-GROUP
    OBJECTS { msdpCacheLifetime, msdpNumSACacheEntries,
              msdpSACacheOriginRP, msdpSACachePeerLearnedFrom,
              msdpSACacheRPFPeer, msdpSACacheInSAs,
         msdpSACacheInDataPackets,
              msdpSACacheUpTime, msdpSACacheExpiryTime,
         msdpSACacheStatus }
    STATUS  current
    DESCRIPTION
            "A collection of objects for managing MSDP SA cache
            entries."
    ::= { msdpMIBGroups 3 }

msdpNotificationGroup NOTIFICATION-GROUP
    NOTIFICATIONS { msdpEstablished,
                    msdpBackwardTransition }
    STATUS  current
    DESCRIPTION
            "A collection of notifications for signaling changes
            in MSDP peer relationships."
    ::= { msdpMIBGroups 4 }

END

-- 
-- Copyright (C) The Internet Society (1999).  All Rights Reserved.
-- 
-- This document and translations of it may be copied and furnished
-- to others, and derivative works that comment on or otherwise
-- explain it or assist in its implmentation may be prepared, copied,
-- published and distributed, in whole or in part, without
-- restriction of any kind, provided that the above copyright notice
-- and this paragraph are included on all such copies and derivative
-- works.  However, this document itself may not be modified in any
-- way, such as by removing the copyright notice or references to the
-- Internet Society or other Internet organizations, except as needed
-- for the purpose of developing Internet standards in which case the
-- procedures for copyrights defined in the Internet Standards
-- process must be followed, or as required to translate it into
-- languages other than English.
-- 
-- The limited permissions granted above are perpetual and will not
-- be revoked by the Internet Society or its successors or assigns.
-- 
-- This document and the information contained herein is provided on
-- an "AS IS" basis and THE INTERNET SOCIETY AND THE INTERNET
-- ENGINEERING TASK FORCE DISCLAIMS ALL WARRANTIES, EXPRESS OR
-- IMPLIED, INCLUDING BUT NOT LIMITED TO ANY WARRANTY THAT THE USE OF
-- THE INFORMATION HEREIN WILL NOT INFRINGE ANY RIGHTS OR ANY IMPLIED
-- WARRANTIES OF MERCHANTABILITY OR FITNESS FOR A PARTICULAR PURPOSE.
-- 
-- 
--
