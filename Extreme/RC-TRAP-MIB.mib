RC-TRAP-MIB DEFINITIONS ::= BEGIN

IMPORTS
    MODULE-IDENTITY, NOTIFICATION-TYPE
        FROM SNMPv2-SMI
    rcTraps,
    rcCardIndex, rcCardAdminStatus, rcCardOperStatus,
    rcChasPowerSupplyId, rcChasPowerSupplyOperStatus,
    rcChasFanId, rcChasFanOperStatus, rcChasFanType, rcChasEmModeError,
    rcCliPasswordChange, rcCliPassChangeResult,
    rcSyslogHostSeverity,
    rcSshGlobalPort, rcSshGlobalHostIpAddr,
    rcSysAction, rcSysMsgLogFrequency, rcSysMsgLogText,
    rcSysConfigFileName, rcSysIpAddr,
    rcSysDnsServerListIpAddr, rcSysDnsRequestType,
    rcSysMacFlapLimitTime, rcSysMacFlapLimitCount,
    rcSysExtCplimitSysOctapidCongested,rcSysExtCplimitPortsMonitored,
    rcCsuGlobalStartUpMode, rcCsuInfoTypeOfCardDesc,rcSysLicenseTrialDaysLeft,
    rcCliPasswordAccountUserName, rcCliPasswordUserAccessLevel, 
    rcLacpMisconfigType, rcSysDnsServerIpv6Addr
        FROM RAPID-CITY
    rcErrorLevel, rcErrorCode, rcErrorText
        FROM RC-ERROR-MIB
    rcStgId, rcStgBridgeAddress,rcBridgeNewFdbAddress
        FROM RC-BRIDGE-MIB
    rcPortIndex, rcPortCpLimitShutDown, rcPortPoeMainPseExtnPwrAdmin,
    rcPortPoePseIndexGroupIndex, rcPortPoePseIndexPortIndex,
    rcPortBpduFilteringTimeout, 
    rcPortUserLabel1, rcPortUserLabel2, rcPortMltId, rcPortRemoteMirroringMode,
    rcPortRemoteMirroringEnable, rcPortRemoteMirroringIndex,
    rcPortCtrlPktDropLimit, rcPortCtrlPktShutdownLimit, rcChannelizedPortAdminMode,
    rcPortBpduGuardTimeout
        FROM RC-PORT-MIB
    pethPsePortDetectionStatus, pethMainPseConsumptionPower
        FROM POWER-ETHERNET-MIB
    rcPosSonetTrapType, rcPosSonetTrapIndication
        FROM RC-POS-MIB
    rc2kCardIndex, rc2kCardFrontAdminStatus,
    rc2kCardFrontOperStatus, rc2kChassisTemperature,
    rc2kChassisBaseMacAddr, rc2kChassisUserLabel1,rc2kDeviceGlobalSlot,
    rc2kCardPerfCPUUtilization
        FROM RC-2K-MIB
    rc2kQosQosRow, rc2kQosQosDropThresholdPercentage,
    rc2kQosQosDropActualPercentage, rc2kQosTotalDropReadings,rc2kQosDropReadings
        FROM RC-2K-QOS-MIB
    rc2kAtmPvcIfIndex, rc2kAtmPvcVpi, rc2kAtmPvcVci, rc2kAtmPvcOamVcStatus
        FROM RC-2K-ATM-MIB
    rcMltId, rcMltSmltId, rcL2RedundancyHaCpuState, rcMltAggTrapEvent
        FROM RC-MLT-MIB
    rcVpnVpnId, rcVpnTunnelLspId, rcVpnRemotePeerId
        FROM RC-OPM-MIB
    rcIpMplsGlobalRouterId
        FROM RC-IP-MPLS-MIB
    ifAdminStatus, ifOperStatus
        FROM IF-MIB
    rcIpBgpPeerIpAddress, rcIpBgpPeerLastError, rcIpBgpPeerState
        FROM RC-IP-BGP-MIB
    rcIgmpGroupIfIndex, rcIgmpGroupIpAddress, rcIgmpGroupInPort,
    rcIgmpGroupMembers, rcIgmpInterfaceIfIndex, rcIgmpInterfaceQuerier, 
    rcIgmpInterfaceExtnNewQuerier
        FROM RC-IGMP-MIB   
    rcVlanId, rcVlanNewLoopDetectedAction, rcVlanName
        FROM RC-VLAN-MIB
    rcTlsTdiEndptTdId, rcTlsTdiEndptUniAddr, rcTlsEndptWatermarkIndication,
    rcTlsTestTdcTestId, rcTlsTdcTestResultIndication,
    rcTlsUniIpServiceWatermarkIndication, rcTlsTdcTestRttExceedIndication,
    rcTlsTdiMdName, rcTlsTdiMaName, rcTlsTdiEndptMepId, 
    rcBanRingId, rcBanRingTrapIndication,
    rcBanRingTrapReason, rcTlsTdiEndptTrunkGroup,
    rcIsidBackboneVlan, rcTlsTdiId, rcTlsSlot, rcTlsIsidId,
    rcBanRingTopoRbsId, rcBanRingTopoRbsMac, rcIsidEndptUserLabel1, rcIsidEndptUserLabel2,
    rcIsidEndptRingId, rcIsidEndptModId, rcIsidEndptEsuPort, rcTlsIpCustIpVlan,
    rcTlsIpCustIpWatermarkIndication, rcTlsRmodLane
        FROM RC-TLS-MIB
    rcPlugOptModTemperatureStatus, rcPlugOptModVoltageStatus,
    rcPlugOptModBiasStatus, rcPlugOptModTxPowerStatus,
    rcPlugOptModRxPowerStatus, rcPlugOptModAux1Monitoring,
    rcPlugOptModAux1Status, rcPlugOptModAux2Monitoring,
    rcPlugOptModAux2Status, rcPluggableModuleDescription
        FROM RC-POM-MIB
    ipNetToMediaPhysAddress, ipNetToMediaNetAddress
        FROM IP-MIB
    rcTacacsGlobalLastUserName,
    rcTacacsGlobalLastAddressType, rcTacacsGlobalLastAddress
        FROM RC-TACACS-MIB
    rcRadiusPaePortNumber, rcRadiusEapLastAuthMac, rcRadiusEapLastRejMac,
    rcRadiusEapRAVErrorMacAddress, rcRadiusEapRAVErrorPort, rcRadiusEapServAddressType,
    rcRadiusEapServAddress
        FROM RC-RADIUS-MIB
    rcCfmEndPointCcmIndication, rcCfmTrunkCcmIndication, rcCfmTrunkMdName,
    rcCfmTrunkMaName, rcCfmTrunkMepId, rcCfmServiceGroupMdName,
    rcCfmServiceGroupMaName, rcCfmServiceGroupMepId, rcCfmServiceGroupCcmIndication,
    rcCfmTrunkGroupProtected, rcCfmTrunkGroupPrimaryTrunk,
    rcCfmTrunkGroupSecondaryTrunk, rcCfmMaintenanceEndPointDomainName,
    rcCfmMaintenanceEndPointAssociationName, rcCfmRemoteMepId,
    rcCfmLocalMepId, rcCfmRemoteMacAddr,
    rcCfmMepCcmIndication, rcCfmIsidId, rcCfmVid, rcCfmCvid,
    rcCfmTrunkGroupActiveTrunk, rcCfmTrunkGroupIndication,
    rcCfmTrunkSourceMac, rcCfmTrapTrunkName,
    rcCfmTrunkReverseVlanId, rcCfmMonitorCosPriority,
    rcCfmThresholdIndication, rcCfmActualPercentage,
    rcCfmActualSubPercentage, rcCfmAlarmThreshold,
    rcCfmAlarmSubThreshold, rcCfmClearThreshold,
    rcCfmClearSubThreshold, rcCfmTrunkUserLabel1,
    rcCfmTrunkUserLabel2, rcCfmFdTarget,
    rcCfmFdAverage, rcCfmFdvTarget, rcCfmDirection,
    rcCfmFdvAverage, rcCfmTrapTrunkGroupName,
    rcCfmTrunkGroupUserLabel1, rcCfmTrunkGroupUserLabel2, rcCfmDhuId,
    rcCfmStatsDefect, rcCfmIftlvIndication
        FROM RC-CFM-MIB
    rcVrfName, rcVrfOperStatus
        FROM RC-VRF-MIB
    lldpRemPortIdSubtype,lldpRemPortId
        FROM LLDP-MIB
    rcBfdTmpSessDiscriminator, rcBfdTmpSessRemoteDiscr, rcBfdTmpSessAddrType, 
    rcBfdTmpSessAddr, rcBfdTmpSessState, rcBfdTmpSessDestAddr, 
    rcBfdTmpSessOldState
        FROM RC-BFD-TMP-MIB
    rcIpResourceUsageGlobalIngressRecInUse,rcIpResourceUsageGlobalEgressRecInUse,
    rcIpResourceUsageGlobalIngressThreshold, rcIpResourceUsageGlobalEgressThreshold 
        FROM RC-IP-MIB
    rcIsisLocalLspId, rcIsisLocall1Metric, rcIsisNgbLspId, rcIsisNgbl1Metric,
    rcIsisPlsbTrapType, rcIsisLocalSysId, rcIsisLocalInterface,
    rcIsisLocalNickname, rcIsisNgbNickname, rcIsisNgbSysId, rcIsisTrapIndicator,
    rcIsisLocalHostName, rcIsisNgbHostName, rcIsisLocalPrimaryBvid,
    rcIsisLocalPrimaryTieBrkAlg, rcIsisLocalSecondaryBvid,
    rcIsisLocalSecondaryTieBrkAlg, rcIsisNgbPrimaryBvid, rcIsisNgbPrimaryTieBrkAlg,
    rcIsisNgbSecondaryBvid, rcIsisNgbSecondaryTieBrkAlg, rcIsisLocalBvidCounter,
    rcIsisNgbBvidCounter, rcIsisLocalVirtualBmac, rcIsisPeerVirtualBmac,
    rcIsisSysId, rcIsisSmltPeerSysId, rcIsisAdjState, rcIsisDuplicateNnameCounter,
    rcIsisLocalSmltSplitBeb, rcIsisPeerSmltSplitBeb, rcIsisPrevInterface,
    rcIsisLocalChassisMac, rcIsisSmltVirtBmacMisconfigNodeSysId, rcIsisSmltVirtBmacMisconfigNodeHostName,
    rcIsisRemoteHostName, rcIsisRemoteChassisMac, rcIsisPreviousSysId
	FROM RC-ISIS-MIB
    rcPrFilterAclId
	FROM RC-POWER-RANGER-MIB
    rcLinkOamTrapIndication, rcLinkOamPeerMacAddress
        FROM RC-LINK-OAM-MIB
    rcLoginUserName, rcLoginHostIpAddress, rcSlotType, rcFanZoneType,
    rcFanTrayId, rcFanUnitId, rcCardTemp, rcCpuUtilization,
    rcLoginHostAddressType, rcLoginHostInetAddress, rcSlotPowerStatus,
    rc2kCardShutDownReason, rc2kCardZoneTemperature, rc2kCardTemperatureZoneInfo
        FROM RC-CB-SWITCH-FABRIC-MIB
    rcWlanNotificationErrorType, rcWlanNotificationTrapInfo,
    rcWlanNotificationMobilityTunnelPeerId,
    rcWlanNotificationMobTunnelAddressType,
    rcWlanNotificationMobTunnelAddress,
    rcWlanNotificationMobTunnelMVlanName
        FROM RC-WLAN-MIB
    rcMldNewGroupIfIndex,
    rcMldNotificationNewGroupIpv6Address,
    rcMldNotificationNewGroupInPort,
    rcMldNotificationNewGroupMembers,
    rcMldNotificationInterfaceIfIndex,
    rcMldInterfaceExtnNewQuerier
    	FROM RC-MLD-MIB
    mldInterfaceQuerier, mldInterfaceIfIndex
        FROM IPV6-MLD-MIB
    rcMRouteIpv6IngressRecInUse, 
    rcMRouteIpv6IngressThreshold,
    rcMRouteIpv6EgressRecInUse, 
    rcMRouteIpv6EgressThreshold
    	FROM RC-MROUTE-IPV6-MIB
    rcLicenseFileName,
    rcLicenseDaysLeftBeforeExpiration,
    rcLicenseDaysAfterExpiration
        FROM RC-LICENSE-MIB
    rcMcastNotificationStreamCountSlot,
    rcMcastNotificationStreamCountLane
    	FROM RC-MCAST-MIB
    rcMsdpVrfId, rcMsdpSACacheType, rcMsdpPeerSALimit
        FROM RC-MSDP-MIB
    msdpPeerFsmEstablishedTransitions, msdpPeerState
        FROM MSDP-MIB
    -- See below for details
    -- rcRestConfServerOperationStatus 
    --    FROM RC-RESTCONF-MIB
    rcIpv6FhsSnoopNotificationEntryType, rcIpv6FhsSnoopNotificationEntryCount
        FROM RC-IPV6-MIB
    rcDigitalCertStatus
        FROM RC-DIGITAL-CERT-MIB;


rcTrapsMib MODULE-IDENTITY
       LAST-UPDATED     "201805090000Z" 
       ORGANIZATION     "Avaya"
       CONTACT-INFO     "Yu-Ten Lee
                         Postal:        Nortel Networks, Inc.
                                        4655 Great America Parkway
                                        Santa Clara, CA 95052-8185

                              Tel:       408-495-2560
                             Fax:        408-495-6680
                         E-mail:         ylee@nortelnetworks.com"
       DESCRIPTION      "Enterprise MIB for the Accelar product family."

       REVISION "201805190000Z" -- 09 May 2018       
       DESCRIPTION "Version 127: Correct the IMPORT syntax for RC-RESTCONF-MIB"

       -- Removing this from the BOSS version of this file, for being unsupported.
       -- REVISION "201804190000Z"  19 Apr. 2018       
       -- DESCRIPTION "Version 126: Added Trap rcnRestconfServerOperationStatusTrap"

       REVISION "201710260000Z" -- 26 Oct 2017
       DESCRIPTION "Version 125: Added rcnIsisPlsbIsisEnabledWithZeroNicknameTrap.
				 Requested by Gautam Khera (hliang)"

       REVISION "201709290000Z" -- 29 Sep 2017
       DESCRIPTION "Version 124: Added rcnIpv6MaxRouteWarnClear, 
	   			 rcnIpv6MaxRouteWarnSet,
                                 rcnIpv6MaxRouteDropClear,
				 rcnIpv6MaxRouteDropSet.
				 Requested by Oana (ppalarapu)"

       REVISION "201704120000Z" -- 12 Apr. 2017
       DESCRIPTION "Version 123: Added rcnRadiusEapRAVError, 
	   			 rcnRadiusEapServersDown,
                                 rcnRadiusEapServerUp.
				 Requested by Alisa Niculescu/Caludiu 
				 Gabriel Mitroi (prempa)"

       REVISION "201702100000Z" -- 10 Feb. 2017
       DESCRIPTION "Version 122: Corrected MIB compiler errors."
       
       REVISION "201701270000Z" -- 27 Jan. 2017
       DESCRIPTION "Version 121: Added rcnIsisPlsbStackableDisableIsisTrap"

       REVISION "201701090000Z" -- 09 Jan 2017
       DESCRIPTION "Version 120: added rcnDvrVistPeerDomainMismatchErrorTrap and
	                         rcnDvrVistPeerDomainMismatchErrorClearTrap."
	   
       REVISION "201612140000Z" -- 14 Dec 2016
       DESCRIPTION "Version 119: added rcnChasPowerSupplyRunningNormal"
	   
       REVISION "201612130000Z" -- 13 Dec 2016
       DESCRIPTION "Version 118: added rcnLicenseNotGranted,
	                               rcnLicenseNotLoaded and
				       rcnLicenseDowngraded"
	   	   
       REVISION "201608170000Z" -- 17 August 2016
       DESCRIPTION "Version 117: added rcnDigitalCertStatusTrap"
	   
       REVISION "201605130000Z" -- 13 May 2016
       DESCRIPTION "Version 116: added rcnSystemUsbInternalAccessErrorTrap"
	   
       REVISION "201604120000Z" -- 12 April 2016
       DESCRIPTION "Version 115: Added rcnMsdpMaxSACacheWarnSetTrap,
	            rcnMsdpMaxSACacheWarnClearTrap,
	            rcnMsdpMaxSACacheErrorSetTrap,
	            rcnMsdpMaxSACacheErrorClearTrap,
	            rcnMsdpMaxPeerSACacheWarnSetTrap,
	            rcnMsdpMaxPeerSACacheWarnClearTrap,
	            rcnMsdpMaxPeerSACacheErrorSetTrap,
	            Trap rcnMsdpMaxPeerSACacheErrorClearTrap,
      	            rcnMsdpMaxPeerSACacheErrorClearTrap,
	            rcnMsdpEstablishedTrap,
	            rcnMsdpBackwardTransitionTrap"

       REVISION "201601260000Z" -- 26 Jan. 2016
       DESCRIPTION "Version 114: Added rcnLicenseWillExpire and rcnLicenseExpired"
	   
       REVISION "201601040000Z" -- 04 Jan. 2016
       DESCRIPTION "Version 113: Corrected rcIpv6FhsSnoopTableFullTrap to
	   			 rcnIpv6FhsSnoopTableFullTrap"
			     
       REVISION "201512080000Z" -- 8 December 2015
       DESCRIPTION "Version 112: added rcnMulticastLaneLimitReachedTrap
	                         Requested by Ankit Barak - (prempa)"

       REVISION "201510190000Z" -- 19 October 2015
       DESCRIPTION "Version 111: added rcIpv6FhsSnoopTableFullTrap
	                         Requested by Shivanand - submit 25855 (prempa)"

       REVISION "201508190000Z" -- 19 August 2015
       DESCRIPTION "Version 110: added rcnBpduGuardPortShutdown and
	                               rcnBpduGuardPortShutdownTimerExpired "
	   
       REVISION "201508140000Z" -- 14 August 2015
       DESCRIPTION "Version 109: Added rcnPlugModInsertedInNotRecommendedPortTra
	                         and rcnPlugModRemovedFromNotRecommendedPortTrap"
	   
       REVISION "201507220000Z" -- 22 July 2015
       DESCRIPTION "Version 108: Changed - 
	   			 rcIsisGlobalDuplicateSysIdRemoteHostName to 
				 rcIsisRemoteHostName.
				 rcIsisGlobalDuplicateSysIdRemoteChassisMac to
				 rcIsisRemoteChassisMac.
				 Added -
				 rcnIsisPlsbLocalDuplicateNnameTrap and
				 rcnIsisPlsbGlobalDuplicateNnameTrap.
	   			 Requested by Gautam Khera (submit 24985) (Prem)"
	   
       REVISION "201506250000Z" -- 25 June 2015
       DESCRIPTION "Version 107: Changed - 
	   			 rcnMRouteIpv6UsageGlobalIngressThresholdExceeded to
				 rcnMRouteIpv6IngressThresholdExceeded.
				 rcnMRouteIpv6UsageGlobalEgressThresholdExceeded to
				 rcnMRouteIpv6EgressThresholdExceeded
	   			 Requested by Andrei Erghelegiu (Prem)"
	   
       REVISION "201506230000Z" -- 23 June 2015
       DESCRIPTION "Version 106: Added - 
	   			 rcnMRouteIpv6UsageGlobalIngressThresholdExceeded and
				 rcnMRouteIpv6UsageGlobalEgressThresholdExceeded 
	   			 Requested by Cristina/Andrei Erghelegiu (Prem)"
	   
       REVISION "201506170000Z" -- 17 June 2015
       DESCRIPTION "Version 105: Added rcnIsisPlsbGlobalDuplicateSysidTrap.
	   			 Requested by Gautam Khera (Prem)"
	   
       REVISION "201504060000Z" -- 6 Apr 2015
       DESCRIPTION "Version 104: Added rcnMldNewGroupMemberTrap,
	   			 rcnMldLossGroupMemberTrap,
				 rcnMldNewQuerierTrap and 
				 rcnMldQuerierChangeTrap.
				 Requested by Stefan Dinescu for MLD - 
				 submit 23004 (Prem)"
	   
       REVISION "201410170000Z" -- 17 Oct 2014
       DESCRIPTION "Version 103: Added rcnDNSv6RequestResponseTrap."
	   
       REVISION "201407020000Z" -- 02 July 2014
       DESCRIPTION "Version 103: Added rcnPortChannelizedStateChangeTrap."
	   
       REVISION "201404220000Z" -- 22 April 2014
       DESCRIPTION "Version 102: Added rcnIsisSpbmSmltVirtBmacMisconfigTrap."

       REVISION "201402140000Z" -- 14 February 2014
       DESCRIPTION "Version 101: Added rcn2kCardOverheat, rcn2kCardZoneOverheat,
	   			 rcn2kCardZoneNormalTemp, rcn2kCardNormalTemp
				 and rcn2kCardOverheatShutDown."

       REVISION "201401220000Z" -- 22 January 2014
       DESCRIPTION "Version 100: Added rcnMaxMacEntriesTrap."

       REVISION "201401130000Z" -- 13 January 2014
       DESCRIPTION "Version 99: Added rcn2kCardShutDownTrap."

       REVISION "201305070000Z" -- 07 May 2013
       DESCRIPTION "Version 98: Changed rcnaBfdNewStatusChange to rcnaBfdStatusChange."

       REVISION "201305070000Z" -- 07 May 2013
       DESCRIPTION "Version 97: Added new trap definitions - rcnaBfdNewStatusChange 
	   	                and rcnaBfdSessExceedThreshold and added 
				rcBfdTmpSessAddrType in the IMPORTS section."

       REVISION "201304120000Z" -- 12 Apr 2013
       DESCRIPTION "Version 96: Added all the necessary objects from RC-BFD-TMP-MIB to IMPORTS section."

       REVISION "201301180000Z" -- 18 Jan 2013
       DESCRIPTION "Version 95: Added rcnSlotPowerAvailableTrap."
	   
       REVISION "201212050000Z" -- 5 Dec 2012
       DESCRIPTION "Version 94: Changed rcnAggLinkMisconfig to rcnLacpMisconfigTrap and added rcLacpMisconfigType object to it."
	   
       REVISION "201211060000Z" -- 6 Nov 2012
       DESCRIPTION "Version 93: Added rcnAggLinkMisconfig."
     
       REVISION "201206200000Z" -- 20 June 2012
       DESCRIPTION "Version 92: Added rcnBfdNewStatusChange."

       REVISION "201204240000Z" -- 24 April 2012
       DESCRIPTION "Version 91: Updated IMPORTS section to address a syntax
                                error and add missing rcIsis.mib objects."

       REVISION "201204050000Z" -- 05 April 2012
       DESCRIPTION "Version 90: Added rcnAuthenticationFailureLoginAttemptsTrap
	   			and rcnUserAccountIdleTimeExpireTrap.
				Added rcCliPasswordAccountUserName and 
				rcCliPasswordUserAccessLevel to the IMPORTS" 

       REVISION "201202210000Z" -- 21 February 2012
       DESCRIPTION "Version 89: Added rcnWlanTrap." 

       REVISION "201110170000Z" -- 17 October 2011
       DESCRIPTION "Version 88: Renamed rcVlacpFlapDetectShutDown to
                                rcnVLacpFlapDetectShutDown and removed
                                several previous trap objects.  This is
                                due to a design change.  The trap has not
                                yet been released to customers."

       REVISION "201110060000Z" -- 06 October 2011
       DESCRIPTION "Version 87: Added rcVlacpFlapDetectShutDown."

       REVISION "201102070000Z" -- 07 February 2011
       DESCRIPTION "Version 86: Added rcLoginHostAddressType,
                                rcLoginHostInetAddress to IMPORTS." 

       REVISION "201102040000Z" -- 04 February 2011
       DESCRIPTION "Version 85: Added rcnaSshSessionLogout,
                                rcnaSshUnauthorizedAccess,
                                rcnaAuthenticationSuccess,
                                rcnaSshSessionLogin."


       REVISION "201101060000Z" -- 06 January 2011
       DESCRIPTION "Version 84: Changed rcIsisSmltPeerBmac to 
	            rcIsisSmltPeerSysId for rcnIsisPlsbSmltPeerBmacMismatchTrap."

       REVISION "201101060000Z" -- 06 January 2011
       DESCRIPTION "Version 83: Added rcIsisLocalHostName and rcIsisNgbHostName
	            to rcnIsisPlsbMetricMismatchTrap. 
		    Added rcIsisTrapIndicator to rcnIsisPlsbDuplicateSysidTrap.
		    Added new traps - 
		    rcnIsisPlsbBvidMismatchTrap, 
		    rcnIsisPlsbSmltVirtBmacMismatchTrap,
		    rcnIsisPlsbSmltPeerBmacMismatchTrap,
		    rcnIsisPlsbAdjStateTrap,
		    rcnIsisPlsbDuplicateNnameTrap,
		    rcnIsisPlsbSmltSplitBebMismatchTrap,
		    rcnIsisPlsbMultiLinkAdjTrap."

       REVISION "201009170000Z" -- 17 September 2010
       DESCRIPTION "Version 82: Added rcLoginUserName,
                                      rcLoginHostIpAddress,
                                      rcSlotType,
                                      rcFanZoneType, rcFanTrayId,
                                      rcFanUnitId,
                                      rcCardTemp,
                                      rcCpuUtilization
                                           to IMPORTS."

       REVISION "201009140000Z" -- 14 September 2010
       DESCRIPTION "Version 81: Added rcnAuthenticationSuccess,
                                      rcnCardInsert,
                                      rcnCardRemove,
                                      rcnChasFanFail,
                                      rcnChasFanOk,
                                      rcnCardOverheat,
                                      rcnCardNormalTemp,
                                      rcnCardOverheatShutDown,
                                      rcnCardCpuUtilizationHigh,
                                      rcnCardCpuUtilizationNormal 
                    as attributes 268-277 respectively under rcTrapsMib group"

       REVISION "200912110000Z" -- 11 December 2009
       DESCRIPTION "Version 80: Added rcnPrFilterRspMemoryFull, rcnPrFilterStatsCntExst
                                as attribute 266, 267 respectively under rcTrapsMib group"

       REVISION "200909100000Z" -- 10 September 2009
       DESCRIPTION "Version 79: Added rcnLegacyCardDetected."

       REVISION "200903250000Z" -- 25 March 2009
       DESCRIPTION "Version 78: Modified name and description of rcTrapsMib 237 to 240."
    
       REVISION "200903170000Z" -- 17 March 2009
       DESCRIPTION "Version 77: Added rcTrapsMib 216 to 264 except 220, 229, 230, 241, 244"

       REVISION "200902200000Z" -- 20 February 2009
       DESCRIPTION "Version 76: Added rcnPimMaxPassiveInterfaceWarnSet."

       REVISION "200902110000Z" -- 11 February 2009
       DESCRIPTION "Version 75: Added rcnPimMaxInterfaceWarnSet and rcnPimMaxNeighborsWarnSet."

       REVISION "200902090000Z" -- 09 February 2009
       DESCRIPTION "Version 74:  SMIv2 cleanup.
                                 Added rcCfmFaultAlarm."

       REVISION "200901270000Z" -- 27 January 2009
       DESCRIPTION "Version 73: Imported rcCfmDhuId, rc2kCardPerfCPUUtilization."

       REVISION "200810030000Z" -- 03 October 2008
       DESCRIPTION "Version 72: Added rcnCfmDualHomeUniClientMepCcmTrap
                                as attribute 211 under rcTrapsMib group"

       REVISION "200809250000Z" -- 25 September 2008
       DESCRIPTION "Version 71: Added traps rcnUpgradeSuccessful,
                                rcnUpgradeFailure, rcnVersionMisMatch,
                                rcnHighCopUtil."

       REVISION "200809220000Z" -- 22 September 2008
       DESCRIPTION "Version 70: Added traps rcnSmpFtpFail,
                                rcnSmpLogFileDeleted."

       REVISION "200808070000Z" -- 07 August 2008
       DESCRIPTION "Version 69: Change rcnDuplexMismatch/rcDuplexMismatch
                                OBJECTS to rcPortIndex."
       
       REVISION "200807240000Z" -- 24 July 2008
       DESCRIPTION "Version 68: Added trap rcnLockupDetected,
					   rcnMacResetForLockup, 
 				   	   rcnModuleResetForLockup,
				    	   rcnModuleFatalError." 	

       REVISION "200807140000Z" -- 14 July 2008
       DESCRIPTION "Version 67: Modified rcnIsisPlsbDuplicateNicknameTrap,
	                                 rcnIsisPlsbMetricMismatchTrap,
					 rcTlsTdiWatermarkTrap,
					 rcTlsIsidWatermarkTrap,
					 rcnFOQDropTrap,
					 rcnFabricDropTrap" 	   
     	   
       REVISION "200806180000Z" -- 18 Jun 2008
       DESCRIPTION "Version 66: Add rcVlanName in IMPORTS clause, update
                                DESCRIPTION of rcn2kGbicRemovedTrap."
       
       REVISION "200806170000Z" -- 17 Jun 2008
       DESCRIPTION "Version 65: Change rcVlanId of rcnRsmltEdgePeerModified to rcVlanName."

       REVISION "200805180000Z" -- 18 May 2008
       DESCRIPTION "Version 64: Imported rcChasFanType."

       REVISION "200805140000Z" -- 14 May 2008
       DESCRIPTION "Version 63: Change trap rcnTripodRSlotActiveTrap to rcnRSlotFabricActiveTrap,
					    rcnTripodRSlotInactiveTrap to rcnRSlotFabricInactiveTrap" 		

       REVISION "200805070000Z" -- 07 May 2008
       DESCRIPTION "Version 62: Added trap rcnFOQDropTrap,
					   rcnFabricDropTrap,
					   rcnTripodRSlotActiveTrap,
					   rcnTripodRSlotInactiveTrap"	

       REVISION "200804190000Z" -- 19 April 2008
       DESCRIPTION "Version 61: Added rcnChasFanCoolingLow as 196th child of rcTrapsMib."

       REVISION "200803170000Z" -- 17 March 2008
       DESCRIPTION "Version 60: Changed traps: rcnBfdSessExceedThreshold, rcnBfdStatusChange"

       REVISION "200803130000Z" -- 13 March 2008
       DESCRIPTION "Version 59: Changed module name to 'RC-VRF-MIB'
from 'RC-VIRTUAL-ROUTING-MIB'."

       REVISION    "200803050000Z" -- 05 March 2008
       DESCRIPTION "Version 58: Added trap rcnCfmEndptClientFlrNearEndTrap,
					   rcnCfmEndptClientFlrFarEndTrap,
					   rcnTosBufferLimitTrap,
					   rcnTosBufferClearTrap,
					   rcnChasCoolingInsufficientTrap,
					   rcnChasCoolingSufficientTrap,
					   rcnIsisPlsbMetricMismatchTrap,
					   rcnIsisPlsbDuplicateSysidTrap,
					   rcnIsisPlsbLsdbUpdateTrap,
					   rcnIsisPlsbDuplicateNicknameTrap
				Modified rcnCfmPortMepCcmExpandedTrap,
				         rcnCfmVlanPortMepCcmExpandedTrap,
					 rcnCfmEndptClientMepCcmExpandedTrap,
					 rcnCfmMltEndptClientMepCcmTrap,
					 rcnCfmVlanMltMepCcmTrap,
					 rcnCfmRingEndptClientMepCcmTrap,
					 rcnCfmTrunkMepCcmExpandedTrap,
					 rcnCfmStandEndptClientMepCcmTrap,
					 rcnCfmDHRingEndptClientMepCcmTrap"   

       REVISION    "200802010000Z" -- 01 Feb 2008
       DESCRIPTION "Version 57: Modified the name of the trap rcnChasPowerSupplyNotEnough to
		    rcnChasPowerSupplyRunningLow"

       REVISION    "200801300000Z" -- 30 Jan 2008
       DESCRIPTION "Version 56: Added trap rcnChasPowerSupplyNotEnough"

       REVISION    "200801100000Z" -- 10 Jan 2008
       DESCRIPTION "Version 55: Added trap rcnBfdSessExceedThreshold, rcnBfdStatusChange"
       
       REVISION    "200712200000Z" -- 20 Dec 2007
       DESCRIPTION "Version 54: Added trap rcnAggLinkStateChange"

       REVISION    "200712060000Z" -- 06 Dec 2007
       DESCRIPTION "Version 53: Added trap rcnMaxMrouteWarnSet, 
                                                                                 rcnMaxMrouteDropSet,
                                                                                 rcnMaxMrouteWarnClear and 
                                                                                 rcnMaxMrouteDropClear ."

       REVISION    "200711201000Z" -- 20 Nov 2007
       DESCRIPTION "Version 52: Added trap rcnRemoteMirroringStatus."
	
       REVISION    "200711200000Z" -- 20 Nov 2007
       DESCRIPTION "Version 51: Added traps rcnMrouteIngressThresholdExceeded and 
			rcnMrouteEgressThresholdExceeded."

       REVISION    "200710180000Z" -- 18 Oct 2007
       DESCRIPTION "Version 50: Modified rc2kCardDown status to obsolete,
                                         rc2kCardUp status to obsolete,
                                Fixed    quotes for rcnMcInRecMoreThanThreshold,
	                                 rcnMcEgRecMoreThanThreshold,
	                        Added    rcSysLicenseTrialDaysLeft,
	                                 rcBridgeNewFdbAddress,
	                                 rc2kDeviceGlobalSlot in IMPORTS section"

       REVISION    "200710150000Z" -- 15 Oct 2007
       DESCRIPTION "Version 49: Updated rcnLicenseTrialPeriodExpiry"

       REVISION    "200710120000Z" -- 12 Oct 2007
       DESCRIPTION "Version 48: Added traps rcnVrfUp, rcnVrfDown"

       REVISION    "200709280000Z" -- 28 Sep 2007
       DESCRIPTION "Version 47: Added traps 171, 172 for licensing"

       REVISION    "200708230000Z" -- 23 Aug 2007
       DESCRIPTION "Version 46: Added rcnCfmDHRingEndptClientMepCcmTrap,
				      rcnChasPowerSupplyNoRedundancy,
				      rcnChasPowerSupplyRedundancy,
				      rcnPortAdminStatusChangeTrap,
				      rcnSaveConfigFailTrap"        


       REVISION    "200708200000Z" -- 20 Aug 2007
       DESCRIPTION "Version 45: Added rcnTmuxParityError"
        
       REVISION    "200707270000Z" -- 27 Jul 2007
       DESCRIPTION "Version 44: Added rcnMcInRecMoreThanThreshold & rcnMcEgRecMoreThanThreshold"

       REVISION    "200707190000Z" -- 19 Jul 2007
       DESCRIPTION "Version 43: Added rcnLinkBadConnection"     

       REVISION    "200706270000Z" -- 27 Jun 2007
       DESCRIPTION "Version 42: Added additional parameters for traps rcnLoopDetectMacDiscard and rcnAutoRecoverLoopDetectedPort"     

       REVISION    "200706010000Z" -- 01 Jun 2007
       DESCRIPTION "Version 41:  Added rcnMltLinkUp and rcnMltLinkDown traps"

       REVISION    "200705040000Z" -- 04 May 2007
       DESCRIPTION "Version 40:  Added 89-109 and 125-159 for OE"

       
       REVISION    "200704030000Z" -- 3 Apr 2007
       DESCRIPTION "Version 39:  Added rcnRsmltEdgePeerModified"

       REVISION    "200703260000Z" -- 26 Mar 2007
       DESCRIPTION "Version 38:  Added rcDuplexMismatch as rcTraps 123 and 
                                 rcnDuplexMismatch as rcTrapsMib 123"
       
       REVISION    "200703160000Z" -- 16 Mar 2007
       DESCRIPTION "Version 37: Obsoleted rcIgmpNewQuerier, rcnIgmpNewQuerier,
                                          rcIgmpQuerierChange, rcnIgmpQuerierChange.
                                Added rcIgmpNewQuerierOnIf, rcnIgmpNewQuerierOnIf,
                                      rcIgmpQuerierChanged, rcnIgmpQuerierChanged"

       REVISION    "200702280000Z" -- 28 Feb 2007
       DESCRIPTION "Version 36: Added rcMstpNewCistRoot, rcMstpNewMstiRoot,
                                rcMstpNewCistRegionalRoot, and rcRstpNewRoot"

       REVISION    "200702230000Z" -- 23 Feb 2007
       DESCRIPTION "Version 35: Add rcnVrfForwardingEnabled and rcnVrfForwardingDisabled."

       REVISION    "200702200000Z" -- 20 Feb 2007
       DESCRIPTION "Version 34: Fixed a MIB compilation error"

       REVISION    "200701300000Z" -- 30 Jan 2007
       DESCRIPTION "Version 33: Added rcnMaxRouteWarnClear, rcnMaxRouteWarnSet, rcnMaxRouteDropClear, 
				rcnMaxRouteDropSet and rcnTrialPeriodExpired (rcTrapsMib 110-114)."

       REVISION    "200701020000Z" -- 02 Jan 2007
       DESCRIPTION "Version 32: Reserved Trap OID 88 -109 for OE feature"

       REVISION    "200602100000Z" -- 10 February 2006
       DESCRIPTION "Version 31: Added rcnCfmTrunkCcmTrap, rcnCfmServiceGroupCcmTrap,
		                      rcnCfmEndPointCcmTrap"

       REVISION    "200602080000Z" -- 08 Feb 2006
       DESCRIPTION "Version 30: Added rcnInterCpuCommStatus"

       REVISION    "200601030000Z" -- 03 Jan 2006
       DESCRIPTION "Version 29: Added missing objects to IMPORTS"

       REVISION    "200512170000Z" -- 17 Dec 2005
       DESCRIPTION "Version 28: Changed trap rcnEapMacIntrusion"

       REVISION    "200512120000Z" -- 12 Dec 2005
       DESCRIPTION "Version 27: Added rcnEapMacIntrusion"

       REVISION    "200510250000Z" -- 25 Oct 2005
       DESCRIPTION "Version 26: Added trap rcnExtCpLimitShutDownNormal."

       REVISION    "200509200000Z" -- 20 September 2005
       DESCRIPTION "Version 25: Fix typo."

       REVISION    "200508050000Z" -- 5 August 2005
       DESCRIPTION "Version 24: Added rcnVlacpPortDown, rcnVlacpPortUp."

       REVISION    "200506200000Z" -- 1 June 2005
       DESCRIPTION "Version 23: Added rcnBpduReceived."

       REVISION    "200506010000Z" -- 1 June 2005
       DESCRIPTION "Version 22: Fixed SMIv2 violations."

       REVISION    "200504140000Z" -- 14 April 2005
       DESCRIPTION "Version 21: Updated rcnTacacsRxUnSupportedFrame.
                                Added rcTraps 39 - 55 as they currently exist
                                in code."

       REVISION    "200504060000Z" -- 06 April 2005
       DESCRIPTION "Version 20: Added TACACS+ traps."

       REVISION    "200503280000Z" -- 28 March 2005
       DESCRIPTION "Version 19: Added rcnTlsUniIpServiceWatermarkTrap trap.
				IMPORT rcTlsUniIpServiceWatermarkIndication"
       
       REVISION    "200503040000Z" -- 04 March 2005
       DESCRIPTION "Version 18: Added rcnNonEapIntrusion trap"

       REVISION    "200501040000Z" -- 04 January 2005
       DESCRIPTION "Version 17: Imports added for rcnExtCpLimitShutDown,
                                rcnExtCpLimitSopCongestion added"
    
       REVISION    "200412210000Z" -- 21 December 2004
       DESCRIPTION "Version 16: Added rcnExtCpLimitShutDown,
                                rcnExtCpLimitSopCongestion"
       
       REVISION    "200409300000Z" -- 30 September 2004
       DESCRIPTION "Version 14: Removed rcVlanNewLoopDetectedMac,
                                rcVlanNewLoopDetectedPortIndex from trap
                                definition."

       REVISION    "200409200000Z" -- 20 September 2004
       DESCRIPTION "Version 13: Changed 'rcnBgpEstablished' and
                                'rcnBgpBackwardTransition' to
		                'rcnbgpEstablished' and
                                'rcnbgpBackwardTransition' to be in sync
                                with the ClearCase branches/releases."

       REVISION    "200409080000Z" -- 08 September 2004
       DESCRIPTION "Version 12: Added rcnLoopDetectMacDiscard,
                                rcnAutoRecoverPort,
                                rcnAutoRecoverLoopDetectedPort trap"

       REVISION    "200408250000Z" -- 25 August 2004
       DESCRIPTION "Version 11:  Added rcnTlsPortWatermark trap"

       REVISION    "200407220000Z" -- 22 July 2004
       DESCRIPTION "Version 10:  Changed description of rcnLoopDetectOnPort"

       REVISION    "200407020000Z" -- 2 July 2004
       DESCRIPTION "Version 9:  Added rcnUnauthorizedAccessToStandByCPU"

       REVISION    "200406240000Z" -- 24 June 2004
       DESCRIPTION "Version 8:  Added rcnLoopDetectPortdown"

       ::= { rcTraps 0 }

rcnCardDown NOTIFICATION-TYPE
        OBJECTS      { rcCardIndex, rcCardAdminStatus, rcCardOperStatus }
        STATUS       current
        DESCRIPTION  "A rcCardDown trap signifies that the SNMPv2 entity,
                     acting in an agent role, has detected that the
                     rcCardOperStatus object for one of its cards 
                     is about to transition into the down state."
        ::= { rcTrapsMib 1 }

rcnCardUp NOTIFICATION-TYPE
        OBJECTS       { rcCardIndex, rcCardAdminStatus, rcCardOperStatus }
        STATUS        current
        DESCRIPTION   "A rcCardUp trap signifies that the SNMPv2 entity,
                      acting in an agent role, has detected that the
                      rcCardOperStatus object for one of its cards 
                      is about to transition into the up state."
        ::= { rcTrapsMib 2 }

rcnErrorNotification NOTIFICATION-TYPE
        OBJECTS       { rcErrorLevel, rcErrorCode, rcErrorText }
        STATUS        current
        DESCRIPTION   "A rcErrorNotification trap signifies that the 
                      SNMPv2 entity, acting in an agent role, has 
                      detected that an error condition has occured."
        ::= { rcTrapsMib 3 }
 
rcnStpNewRoot NOTIFICATION-TYPE
        OBJECTS       { rcStgId }
        STATUS        current
        DESCRIPTION   "A rcStpNewRoot trap signifies that the
                      SNMPv2 entity, acting in an agent role, has
                      detected the Spanning Tree Protocol has declared
                      the device to be the new root of the spanning 
       		      tree." 
        ::= { rcTrapsMib 4 }

rcnStpTopologyChange NOTIFICATION-TYPE
       OBJECTS        { rcStgId, rcPortIndex }
       STATUS         current   
       DESCRIPTION    "A rcStpTopologyChange trap signifies that the 
                      SNMPv2 entity, acting in an agent role, has 
                      detected the Spanning Tree Protocol has gone due
                      a topology change event."
       ::= { rcTrapsMib 5 }

rcnChasPowerSupplyDown NOTIFICATION-TYPE
        OBJECTS       { rcChasPowerSupplyId, rcChasPowerSupplyOperStatus}
        STATUS        current
        DESCRIPTION   "A rcChasPowerSupplyDown trap signifies that the 
                      SNMPv2 entity, acting in an agent role, has 
                      detected that the rcChasPowerSupplyOperStatus 
                      object for one of its power supply unit is 
                      about to transition into the down state."
        ::= { rcTrapsMib 6 }

rcnChasFanDown NOTIFICATION-TYPE
        OBJECTS       { rcChasFanId, rcChasFanOperStatus}
        STATUS        current
        DESCRIPTION   "A rcChasFanDown trap signifies that the 
                      SNMPv2 entity, acting in an agent role, has 
                      detected that the rcChasFanOperStatus object 
                      for one of its power supply unit is about to 
                      transition into the down state."
        ::= { rcTrapsMib 7 }

rcnLinkOscillation NOTIFICATION-TYPE
        OBJECTS          { rcPortIndex }
        STATUS             current
        DESCRIPTION   "A rcLinkOscillation trap signifies that the
                       SNMPv2 entity, acting in an agent role, has
                       detected an excessive number of link state
                       transitions on the specified port."
        ::= { rcTrapsMib 8 }

rcnMacViolation NOTIFICATION-TYPE	
        OBJECTS       { rcErrorText, rcPortIndex }
        STATUS        current
        DESCRIPTION   "A rcMacViolation trap signifies that the
                      SNMPv2 entity, acting in an agent role, has
                      received a PDU with an invalid source MAC
                      address."
        ::= { rcTrapsMib 9 }

rcnSonetTrap NOTIFICATION-TYPE
        OBJECTS       { rcPortIndex, rcPosSonetTrapType, rcPosSonetTrapIndication }
        STATUS        current
        DESCRIPTION   "A rcSonetTrap trap signifies that the
                      SNMPv2 entity, acting in an agent role, has
                      detected a change of status on a Sonet port."
        ::= { rcTrapsMib 10 }

rcn2kCardDown NOTIFICATION-TYPE
        OBJECTS      { rc2kCardIndex, 
                       rc2kCardFrontAdminStatus, 
                       rc2kCardFrontOperStatus }
        STATUS       current
        DESCRIPTION  "A rcCardDown trap signifies that the SNMPv2 entity,
                     acting in an agent role, has detected that the
                     rcCardOperStatus object for one of its cards
                     is about to transition into the down state."
        ::= { rcTrapsMib 11 }

rcn2kCardUp NOTIFICATION-TYPE
        OBJECTS       { rc2kCardIndex, 
                        rc2kCardFrontAdminStatus, 
                        rc2kCardFrontOperStatus }
        STATUS        current
        DESCRIPTION   "A rcCardUp trap signifies that the SNMPv2 entity,
                      acting in an agent role, has detected that the
                      rcCardOperStatus object for one of its cards
                      is about to transition into the up state."
        ::= { rcTrapsMib 12 }

rcn2kTemperature NOTIFICATION-TYPE
        OBJECTS       { rc2kChassisTemperature }
        STATUS        current
        DESCRIPTION   "A rc2kTemperature trap signifies that the SNMPv2 
		      entity, acting in an agent role, has detected the
                      chassis is over-heating."
        ::= { rcTrapsMib 13 }

rcnChasPowerSupplyUp NOTIFICATION-TYPE
        OBJECTS       { rcChasPowerSupplyId, rcChasPowerSupplyOperStatus}
        STATUS        current
        DESCRIPTION   "A rcChasPowerSupplyUp trap signifies that the
                      SNMPv2 entity, acting in an agent role, has
                      detected that the rcChasPowerSupplyOperStatus
                      object for one of its power supply unit is
                      about to transition into the up state."
        ::= { rcTrapsMib 14 }

rcn2kAtmPvcLinkStateChange NOTIFICATION-TYPE
        OBJECTS       { rc2kAtmPvcIfIndex, 
                        rc2kAtmPvcVpi, 
                        rc2kAtmPvcVci, 
                        rc2kAtmPvcOamVcStatus }    
        STATUS        current
        DESCRIPTION   "A rc2kAtmPvcLinkStateChange trap signifies that the 
                       SNMPv2 entity, acting in an agent role, has detected 
                       that the rc2kAtmPvcOamVcStatus object for one of PVC is
                       about to transition into different state, either from 
                       up to down or from down to up."
        ::= { rcTrapsMib 15 } 

rcnStpTCN NOTIFICATION-TYPE
       OBJECTS        { rcStgId, rcPortIndex, rcStgBridgeAddress }
       STATUS         current
       DESCRIPTION    "A rcStpTopologyChange trap signifies that the
                      SNMPv2 entity, acting in an agent role, has
                      detected the Spanning Tree Protocol has gone due
                      a topology change event."
       ::= { rcTrapsMib 16 }

rcnSmltIstLinkUp NOTIFICATION-TYPE
        STATUS        current
        DESCRIPTION   "A rcSmltIstLinkUp trap signifies that the split
                      MLT link is from down to up."
        ::= { rcTrapsMib 17 }

rcnSmltIstLinkDown NOTIFICATION-TYPE
        STATUS        current
        DESCRIPTION   "A rcSmltIstLinkDown trap signifies that the
                      split MLT link is from up to down."
        ::= { rcTrapsMib 18 }

rcnSmltLinkUp NOTIFICATION-TYPE
        OBJECTS       { rcMltSmltId }
        STATUS        current
        DESCRIPTION   "A rcMltSmltId trap signifies that the split 
                      SMLT link is up."
        ::= { rcTrapsMib 19 }

rcnSmltLinkDown NOTIFICATION-TYPE
        OBJECTS       { rcMltSmltId }
        STATUS        current
        DESCRIPTION   "A rcMltSmltId trap signifies that the split 
                      SMLT link is down."
        ::= { rcTrapsMib 20 }

rcnChasFanUp NOTIFICATION-TYPE
        OBJECTS       { rcChasFanId, rcChasFanOperStatus}
        STATUS        current
        DESCRIPTION   "A rcChasFanUp trap signifies that the
                      SNMPv2 entity, acting in an agent role, has
                      detected that the rcChasFanOperStatus object
                      for one of its power supply unit is about to
                      transition into the up state."
        ::= { rcTrapsMib 21 }

rcnPasswordChange NOTIFICATION-TYPE
        OBJECTS       { rcCliPasswordChange, rcCliPassChangeResult}
        STATUS        current
        DESCRIPTION   "A rcPasswordChange trap signifies that the
                      SNMPv2 entity, acting in an agent role, has
                      detected that the one of the cli password is
                      changed."
        ::= { rcTrapsMib 22 }

rcnEmError NOTIFICATION-TYPE
        OBJECTS       { rc2kCardIndex, rcChasEmModeError}
        STATUS        current
        DESCRIPTION   "A rcEmError trap signifies that the
                      SNMPv2 entity, acting in an agent role, has
                      detected Em error."
        ::= { rcTrapsMib 23 }

rcnVpnTrap NOTIFICATION-TYPE
        OBJECTS       { rcVpnVpnId, rcErrorText, rcVpnTunnelLspId,
                        rcIpMplsGlobalRouterId, rcVpnRemotePeerId, 
                        rcSyslogHostSeverity}    
        STATUS        current
        DESCRIPTION   "L2Vpn will send trap when the Lsp goes down, which
                       would affect the operational status of the Vpn (given
                       by the VpnId). The Cause will indicate the reason for
                       sending the trap. It can either LSP down/failure or
                       to the bandwidth requirements cannot be fulfilled.
                       Severity Level can be Warning/Error/Fatal."
        ::= { rcTrapsMib 24 }

rcnPcmciaCardRemoved NOTIFICATION-TYPE
        STATUS        current
        DESCRIPTION   "A rcPcmciaRemoved trap signifies that the
                      SNMPv2 entity, acting in an agent role, has
                      detected that the PCMCIA card is being removed."
        ::= { rcTrapsMib 25 }

rcnSmartCpldTimerFired NOTIFICATION-TYPE
        OBJECTS       { rc2kCardIndex }
        STATUS        current
        DESCRIPTION   "A rcSmartCpldTimerFired trap signifies that the
                       cpld timer fired."
        ::= { rcTrapsMib 26 }

rcnCardCpldNotUpDate NOTIFICATION-TYPE
        OBJECTS       { rc2kCardIndex }
        STATUS        current
        DESCRIPTION   "A rcCardCpldNotUpDate trap signifies that the
                       cpld is not up to date."
        ::= { rcTrapsMib 27 }

rcnIgapLogFileFull NOTIFICATION-TYPE
        STATUS        current
        DESCRIPTION   "A rcIgapLogFileFull trap signifies that the
                       Igap accounting time-out Log File reach the 
                       maximum."
        ::= { rcTrapsMib 28 }

rcnCpLimitShutDown NOTIFICATION-TYPE
        OBJECTS       { rcPortIndex, 
                        ifAdminStatus,
                        ifOperStatus,
                        rcPortCpLimitShutDown } 
        STATUS        current
        DESCRIPTION   "A rcCpLimitShutDown trap signifies that the
                       cp limit for the port is shutting down."
        ::= { rcTrapsMib 29 }

rcnSshServerEnabled NOTIFICATION-TYPE
        OBJECTS       { rcSshGlobalPort }
        STATUS        current
        DESCRIPTION   "A rcSshServerEnabled trap signifies that the
                       SSH server is enabled."
        ::= { rcTrapsMib 30 }

rcnSshServerDisabled NOTIFICATION-TYPE
        OBJECTS       { rcSshGlobalPort }
        STATUS        current
        DESCRIPTION   "A rcSshServerDisabled trap signifies that the
                       SSH server is disabled."
        ::= { rcTrapsMib 31 }

rcnSshSessionLogin NOTIFICATION-TYPE
        OBJECTS       { rcSshGlobalHostIpAddr }
        STATUS        current
        DESCRIPTION   "A rcSshSessionLogin trap signifies that there
                       is a SSH session login."
        ::= { rcTrapsMib 32 }

rcnSshSessionLogout NOTIFICATION-TYPE
        OBJECTS       { rcSshGlobalHostIpAddr }
        STATUS        current
        DESCRIPTION   "A rcSshSessionLogout trap signifies that there
                       is a SSH session logout."
        ::= { rcTrapsMib 33 }

rcnSshUnauthorizedAccess NOTIFICATION-TYPE
        OBJECTS       { rcSshGlobalHostIpAddr }
        STATUS        current
        DESCRIPTION   "A rcSshUnauthorizedAccess trap signifies that
                       an unauthorized access has occured."
        ::= { rcTrapsMib 34 }

rcnHaCpuState NOTIFICATION-TYPE
        OBJECTS       { rc2kCardIndex, rcL2RedundancyHaCpuState }
        STATUS        current
        DESCRIPTION   "A rcHaCpuState trap signifies that the
                       state of the HA-CPU."
        ::= { rcTrapsMib 35 }

rcnInsufficientMemory NOTIFICATION-TYPE
        OBJECTS       { rc2kCardIndex}
        STATUS        current
        DESCRIPTION   "A rcInsufficientMemory trap indicates insufficient memory on
                       CPU blade for proper operation. Recommended memory = 256 MB 
                       available through Nortel Networks upgrade kit"
        ::= { rcTrapsMib 36 }

rcnSaveConfigAction NOTIFICATION-TYPE
        OBJECTS       { rcSysAction }
        STATUS        current
        DESCRIPTION   "A rcSaveConfigAction trap indicates the switch run
                       time or boot configuration is being saved"
        ::= { rcTrapsMib 37 }

rcnLoopDetectOnPort NOTIFICATION-TYPE
        OBJECTS       { rcVlanId, rcPortIndex }
        STATUS        current
        DESCRIPTION   "A rcnLoopDetectOnPort trap indicates that a loop has
                       been detected on a port. The vlan on that port will
                       be disabled."
        ::= { rcTrapsMib 38 }

rcnbgpEstablished NOTIFICATION-TYPE
        OBJECTS { rcIpBgpPeerIpAddress,
                  rcIpBgpPeerLastError,
                  rcIpBgpPeerState      }
        STATUS  current
        DESCRIPTION
                "The BGP Established event is generated when
                 the BGP FSM enters the ESTABLISHED state."
        ::= { rcTrapsMib 39 }

rcnbgpBackwardTransition NOTIFICATION-TYPE
        OBJECTS { rcIpBgpPeerIpAddress,
                  rcIpBgpPeerLastError,
                  rcIpBgpPeerState      }
        STATUS  current
        DESCRIPTION
                "The BGPBackwardTransition Event is generated
                 when the BGP FSM moves from a higher numbered
                 state to a lower numbered state."
        ::= { rcTrapsMib 40 }

rcnAggLinkUp NOTIFICATION-TYPE
        OBJECTS       { rcMltId }
        STATUS        current
        DESCRIPTION   "A rcAggLinkUp trap is generated when the operational
                       state of the aggregator changes from down to up."
        ::= { rcTrapsMib 41 }

rcnAggLinkDown NOTIFICATION-TYPE
        OBJECTS       { rcMltId }
        STATUS        current
        DESCRIPTION   "A rcAggLinkDown trap is generated when the operational
                       state of the aggregator changes from up to down."
        ::= { rcTrapsMib 42 }

rcnIgmpNewGroupMember NOTIFICATION-TYPE
        OBJECTS       { rcIgmpGroupIfIndex,
                        rcIgmpGroupIpAddress,
                        rcIgmpGroupInPort,
                        rcIgmpGroupMembers }
        STATUS        current
        DESCRIPTION   "An IgmpNewGroupMember  trap signifies that a
                       new member has come on an interface."
        ::= { rcTrapsMib 43 }

rcnIgmpLossGroupMember NOTIFICATION-TYPE
        OBJECTS       { rcIgmpGroupMembers,
                        rcIgmpGroupIpAddress,
                        rcIgmpGroupInPort,
                        rcIgmpGroupIfIndex }
        STATUS        current
        DESCRIPTION   "An IgmpLossGroupMember  trap signifies that a
                       group member has been lost on an interface."
        ::= { rcTrapsMib 44 }

rcnIgmpNewQuerier NOTIFICATION-TYPE
-- cannot include igmpInterfaceIfIndex in the OBJECTS clause because it
-- is not-accessible
--        OBJECTS       { igmpInterfaceIfIndex,
--                        igmpInterfaceQuerier }
        STATUS        obsolete
        DESCRIPTION   "An igmpNewQuerier trap signifies that a new
                       querier has come up on an interface."
        ::= { rcTrapsMib 45 }

rcnIgmpQuerierChange NOTIFICATION-TYPE
-- cannot include igmpInterfaceIfIndex in the OBJECTS clause because it
-- is not-accessible
--        OBJECTS       { igmpInterfaceIfIndex,
--                        rcIgmpInterfaceExtnNewQuerier,
--                        igmpInterfaceQuerier }
        STATUS        obsolete
        DESCRIPTION   "An rcIgmpQuerierChange trap signifies that
                       the querier has changed."
        ::= { rcTrapsMib 46 }

rcnDvmrpIfStateChange NOTIFICATION-TYPE
-- Cannot use these, as they are either not-accessible, or no longer exist
-- in the current draft of the DVMRP-STD-MIB
--        OBJECTS       { dvmrpInterfaceIfIndex,
--                        dvmrpInterfaceOperState }
        STATUS        current
        DESCRIPTION   "A rcDvmrpIfStateChange trap signifies that there
                       has been a change in the state of a DVMRP
                       interface."
        ::= { rcTrapsMib 47 }

rcnDvmrpNewNbrChange NOTIFICATION-TYPE
-- Cannot use these, as they are either not-accessible, or no longer exist
-- in the current draft of the DVMRP-STD-MIB
--        OBJECTS       { dvmrpNeighborIfIndex,
--                        dvmrpNeighborAddress }
        STATUS        current
        DESCRIPTION   "A rcDvmrpNewNbrChange trap signifies that a new
                       neighbor has come up on a DVMRP interface."
        ::= { rcTrapsMib 48 }

rcnDvmrpNbrLossChange NOTIFICATION-TYPE
-- Cannot use these, as they are either not-accessible, or no longer exist
-- in the current draft of the DVMRP-STD-MIB
--        OBJECTS       { dvmrpNeighborIfIndex,
--                        dvmrpNeighborAddress }
        STATUS        current
        DESCRIPTION   "A rcDvmrpNbrLossChange trap signifies that a new
                       neighbor has gone down on a DVMRP interface."
        ::= { rcTrapsMib 49 }

rcnPsePortOnOff NOTIFICATION-TYPE
-- Cannot include pethPsePortGroupIndex or pethPsePortIndex in OBJECTS
-- clause because they are not-accessible
--        OBJECTS       { pethPsePortGroupIndex,
--                        pethPsePortIndex,
--                        pethPsePortDetectionStatus }
        STATUS        current
        DESCRIPTION   "A rcPsePortOnOff trap signifies that if
                       Pse Port is delivering or not power to the
                       This Notification SHOULD be sent on every
                       status change except in the searching mode."
        ::= { rcTrapsMib 50 }

rcnPsePortPowerMaintenanceStatus NOTIFICATION-TYPE
-- pethPsePortPowerMaintenanceStatus no longer exists, cannot use it here
-- Also, cannot include pethPsePortGroupIndex or pethPsePortIndex in OBJECTS
-- clause because they are not-accessible
--        OBJECTS       { pethPsePortGroupIndex,
--                        pethPsePortIndex,
--                        pethPsePortPowerMaintenanceStatus }
        STATUS        current
        DESCRIPTION   "A rcPsePortPowerMaintenanceStatus trap
                       signifies that a Port change Status and
                       it SHOULD be sent on every status change."
        ::= { rcTrapsMib 51 }

rcnMainPseBackupActivate NOTIFICATION-TYPE
-- Cannot include pethPsePortGroupIndex or pethPsePortIndex in OBJECTS
-- clause because they are not-accessible
--        OBJECTS       { pethPsePortGroupIndex,
--                        pethPsePortIndex,
--                        pethMainPseBackupActivated }
        STATUS        current
        DESCRIPTION   "A rcMainPseBackupActivate trap signifies that
                       a Backup is Activated or BackUp is released
                       on a Pse Port Group."
        ::= { rcTrapsMib 52 }

rcnMainPowerUsageOn NOTIFICATION-TYPE
-- Cannot include pethPsePortGroupIndex or pethPsePortIndex in OBJECTS
-- clause because they are not-accessible
--        OBJECTS       { pethPsePortGroupIndex,
--                        pethMainPseConsumptionPower }
        STATUS        current
        DESCRIPTION   "A rcMainPowerUsageOn trap signifies that
                       PSE Threshold Usage indication of a PSE
                       Port Group is on, the usage power is above
                       the threshold."
        ::= { rcTrapsMib 53 }

rcnMainPowerUsageOff NOTIFICATION-TYPE
-- Cannot include pethPsePortGroupIndex or pethPsePortIndex in OBJECTS
-- clause because they are not-accessible
--        OBJECTS       { pethPsePortGroupIndex,
--                        pethMainPseConsumptionPower }
        STATUS        current
        DESCRIPTION   "A rcMainPowerUsageOn trap signifies that
                       PSE Threshold Usage indication of a PSE
                       Port Group is off, the usage power is above
                       the threshold."
        ::= { rcTrapsMib 54 }

rcnPseCardOnOff NOTIFICATION-TYPE
        OBJECTS       { rcPortPoeMainPseExtnPwrAdmin }
        STATUS        current
        DESCRIPTION   "A rcPoeMainPwrFailure trap signifies that the
                       main power admin status is up."
        ::= { rcTrapsMib 55 }

rcnTlsWatermarkTrap NOTIFICATION-TYPE
         OBJECTS       { rcTlsTdiEndptTdId,
                         rcTlsTdiEndptUniAddr,
                         rcTlsEndptWatermarkIndication}
        STATUS        current
        DESCRIPTION   "A Watermark trap signifies that the Mac Table for the
                       endpoint has reached its high watermark or is already
                       full."
        ::= { rcTrapsMib 56 }

rcnTdcTestResultTrap NOTIFICATION-TYPE
        OBJECTS       { rcTlsTestTdcTestId,
                        rcTlsTdcTestResultIndication }
        STATUS        current
        DESCRIPTION   "A Tdc test fail trap indicates that the tdc test
                       test identified by test ID failed."
        ::= { rcTrapsMib 57 }

rcnTdcTestRttExceedTrap NOTIFICATION-TYPE
        OBJECTS       { rcTlsTestTdcTestId,
                        rcTlsTdcTestRttExceedIndication }
        STATUS        current
        DESCRIPTION   "A Tdc Rtt Exceed trap indicates that the round trip
                       time of the tdc test identified by test ID exceeded
                       the configured threshold value."
        ::= { rcTrapsMib 58 }

rcnFdbProtectViolation NOTIFICATION-TYPE
        OBJECTS { rcPortIndex,
                  rcVlanId }
        STATUS  current
        DESCRIPTION
                "The rcFdbProtectViolation trap signifies that the
                 port has violated the user configured limit for
                 total number of fdb-entries learned on that port."
        ::= { rcTrapsMib 59 }

rcnLogMsgControl NOTIFICATION-TYPE
        OBJECTS { rcSysMsgLogFrequency, rcSysMsgLogText }
        STATUS  current
        DESCRIPTION
                "A rcMsgControl trap signifies whether the number of times of
                 repeatation of the particular Log message has exceeded
                 the particular frequency/count or not."
        ::= { rcTrapsMib 60 }

rcnSaveConfigFile       NOTIFICATION-TYPE
        OBJECTS       { rcSysAction, rcSysConfigFileName }
        STATUS        current
        DESCRIPTION   "A rcSaveConfig trap signifies that either the
                       runtime config or the boot config has been saved
                       on the switch"
        ::= { rcTrapsMib 61 }

rcnDNSRequestResponse NOTIFICATION-TYPE
        OBJECTS       { rcSysDnsServerListIpAddr, rcSysDnsRequestType }
        STATUS        current
        DESCRIPTION  
	 "A rcDnsRequestResponse trap signifies that the
                       switch had sent a query to the DNS server or it had
                       received a successful response from the DNS Server"
        ::= { rcTrapsMib 62 }

rcnDuplicateIpAddress NOTIFICATION-TYPE
        OBJECTS       { ipNetToMediaNetAddress , ipNetToMediaPhysAddress }
        STATUS        current
        DESCRIPTION  
	 "A rcDuplicateIpAddressTrap signifies that a duplicate IP
                       address is detected on the subnet"
        ::= { rcTrapsMib 63 }

rcnLoopDetectPortDown NOTIFICATION-TYPE
        OBJECTS       { rcPortIndex,  ifAdminStatus, ifOperStatus }
        STATUS        current
        DESCRIPTION  
	 "A rcLoopDetectPortDown trap signifies that a loop has
                        been detected on a port and the port is going to shut down."
        ::= { rcTrapsMib 64 }

rcnUnauthorizedAccessToStandByCPU NOTIFICATION-TYPE
        OBJECTS       { rcSysIpAddr }
        STATUS        current
        DESCRIPTION   "A rcnUnauthorizedAccessToStandByCPU trap
                       signifies that the user attempt to access
                       standby CPU."
        ::= { rcTrapsMib 65 }

rcnTlsPortWatermarkTrap  NOTIFICATION-TYPE
        OBJECTS       { rcPortIndex,  
                        rcTlsEndptWatermarkIndication}
        STATUS        current
        DESCRIPTION   "A Watermark trap signifies that the
                       Mac Table for the port has reached its high watermark or already full"
        ::= { rcTrapsMib 66 }

rcnLoopDetectMacDiscard NOTIFICATION-TYPE
        OBJECTS  { rcBridgeNewFdbAddress,rcPortIndex,rcPortIndex, rcSysMacFlapLimitTime, rcSysMacFlapLimitCount}
        STATUS     current
        DESCRIPTION  "A rcLoopDetectMacDiscard  trap signifies that a loop 
                      has been Detected on a port and the mac address will 
                      be discarded on all ports in that vlan"
        ::= { rcTrapsMib 67}

rcnAutoRecoverPort NOTIFICATION-TYPE
        OBJECTS { rcPortIndex }
        STATUS current
        DESCRIPTION "A rcnAutoRecoverPort trap signifies that autorecover 
                     has re-enabled a port disabled by link flap or cp limit"
        ::= {rcTrapsMib 68 }

rcnAutoRecoverLoopDetectedPort NOTIFICATION-TYPE
        OBJECTS {  rcPortIndex,rcVlanNewLoopDetectedAction }
        STATUS current
        DESCRIPTION "A rcnAutoRecoverPort trap signifies that autorecover 
                     has cleared the action taken on a port by loop detect"
        ::= {rcTrapsMib 69 }

rcnExtCpLimitShutDown NOTIFICATION-TYPE
         OBJECTS       { rcPortIndex,
                         ifAdminStatus
                       }
         STATUS        current
         DESCRIPTION  "A rcnExtCpLimitShutDown trap signifies that
                       port is shut down due to Extended CP-Limit."
         ::= { rcTrapsMib 70 }
 
rcnExtCpLimitSopCongestion NOTIFICATION-TYPE
         OBJECTS       { rcSysExtCplimitSysOctapidCongested,
                         rcSysExtCplimitPortsMonitored
                       }
         STATUS        current
         DESCRIPTION  "A rcnExtCpLimitSopCongestion signifies that system octapid
                       polling finds that system octapid is congested or not.
                       rcSysExtCplimitSysOctapidCongested signifies whether 
                       system octapid is congested or not.
                       rcSysExtCplimitPortsMonitored signifies whether ports are
                       selected for monitoring the ingress traffic utilization."
         ::= {rcTrapsMib 71 }

rcnNonEapIntrusion NOTIFICATION-TYPE
        OBJECTS       { rcErrorText, rcPortIndex }
        STATUS        current
        DESCRIPTION   "A rcNonEapIntrusion trap signifies that the
                      an intrusion has occurred in the port. This occurs when
                      the number of non-eap clients exceed the maximum allowed
                      non-eap clients on the port "
        ::= { rcTrapsMib 72 }

rcnTlsUniIpServiceWatermarkTrap  NOTIFICATION-TYPE
        OBJECTS       { rcTlsUniIpServiceWatermarkIndication}
        STATUS        current
        DESCRIPTION   "A Watermark trap signifies that the Ip Table for the Uni Ip Service (Cust Ip)  
		has reached its high watermark or already full"
        ::= { rcTrapsMib 73 }

rcnTacacsAuthFailure NOTIFICATION-TYPE
    OBJECTS       { rcTacacsGlobalLastUserName }
    STATUS        current
    DESCRIPTION   "TACACS+ authentication failed for user"
    ::= { rcTrapsMib 74 }

rcnTacacsNoServers NOTIFICATION-TYPE
    STATUS        current
    DESCRIPTION   "Unable to use any TACACS+ servers for authentication"
    ::= { rcTrapsMib 75 }

rcnTacacsRxUnsupportedFrame NOTIFICATION-TYPE
    OBJECTS       { rcTacacsGlobalLastAddressType, rcTacacsGlobalLastAddress }
    STATUS        current
    DESCRIPTION   "Received unsupported frame from TACACS+ server"
    ::= { rcTrapsMib 76 }

rcnTacacsExceededMaxLogins NOTIFICATION-TYPE
    STATUS        current
    DESCRIPTION   "Attempted to exceed the maximum number of allowed TACACS+ logins"
    ::= { rcTrapsMib 77 }

rcnTacacsClientFailure NOTIFICATION-TYPE
    STATUS        current
    DESCRIPTION   "TACACS+ Client application is down"
    ::= { rcTrapsMib 78 }


rcnBpduReceived NOTIFICATION-TYPE
    OBJECTS       { rcPortBpduFilteringTimeout }
    STATUS        current
    DESCRIPTION   "This notification will be generated when a BPDU is
                   received on a port which has BPDU filtering enabled."
    ::= { rcTrapsMib 79 }

rcnVlacpPortDown NOTIFICATION-TYPE
    OBJECTS       { rcPortIndex}
    STATUS        current
    DESCRIPTION  "A rcnVlacpPortDown trap signifies that
                  Vlacp is down on the port specified."
    ::= { rcTrapsMib 80 }

rcnVlacpPortUp NOTIFICATION-TYPE
    OBJECTS       { rcPortIndex}
    STATUS        current
    DESCRIPTION  "A rcnVlacpPortUp trap signifies that
                 Vlacp is Up on the port specified."
    ::= { rcTrapsMib 81 }

rcnExtCpLimitShutDownNormal NOTIFICATION-TYPE
    STATUS        current
    DESCRIPTION  "An rcnExtCpLimitShutDownNormal trap signifies that
                 Ports are shut down due to Extended CP-Limit in Normal mode."
    ::= { rcTrapsMib 82 }

rcnEapMacIntrusion NOTIFICATION-TYPE
     OBJECTS      {rcSysIpAddr, rcRadiusPaePortNumber,
                   rcRadiusEapLastAuthMac, rcRadiusEapLastRejMac}
     STATUS       current
     DESCRIPTION  "A rcnEapMacIntrusion trap signifies that 
                   an EAP MAC intrusion had occurred on this port."
     ::= { rcTrapsMib 83 }

rcnInterCpuCommStatus NOTIFICATION-TYPE 
     OBJECTS      { rc2kCardIndex, rcCardOperStatus }
     STATUS        current
     DESCRIPTION  "A rcnInterCpuCommStatus trap signifies the
                   current communication status between primary 
                   and secondary CPU."
     ::= { rcTrapsMib 84 }

rcnCfmTrunkCcmTrap  NOTIFICATION-TYPE
     OBJECTS       { rcCfmTrunkMdName,  
                     rcCfmTrunkMaName,
                     rcCfmTrunkMepId,
                     rcCfmTrunkCcmIndication}
     STATUS        current
     DESCRIPTION   "A TrunkCcm trap signifies that the
                    trunk CCM operational state has been changed"
     ::= { rcTrapsMib 85 }

rcnCfmServiceGroupCcmTrap  NOTIFICATION-TYPE
     OBJECTS       { rcCfmServiceGroupMdName,  
                     rcCfmServiceGroupMaName,
                     rcCfmServiceGroupMepId,
                     rcCfmServiceGroupCcmIndication}
     STATUS        current
     DESCRIPTION   "A ServiceGroupCcm trap signifies that the
                    Service Group CCM operational state has been changed"
     ::= { rcTrapsMib 86 }

rcnCfmEndPointCcmTrap  NOTIFICATION-TYPE
        OBJECTS       { rcTlsTdiMdName,  
                        rcTlsTdiMaName,
                        rcTlsTdiEndptMepId,
                        rcCfmEndPointCcmIndication}
        STATUS        current
        DESCRIPTION   "A ServiceGroupCcm trap signifies that the
                       Service Group CCM operational state has been changed"
      ::= { rcTrapsMib 87 }


rcnBanRingStateChangeTrap NOTIFICATION-TYPE
        OBJECTS       { rcBanRingId,
                        rcBanRingTrapIndication,
                        rcBanRingTrapReason}
        STATUS        current
        DESCRIPTION   "A ring State change Trap" 
        ::= { rcTrapsMib 88 }

-- The following are traps that will notify the network management of changes
-- in the status (normal,warning,alarm) of DDI variables

rcPlugOptModTemperatureStatusTrap NOTIFICATION-TYPE
        OBJECTS      { rcPortIndex, rcPlugOptModTemperatureStatus }
        STATUS       current
        DESCRIPTION "Used to trap changes in the temperature status"
        ::= { rcTrapsMib 89}

rcPlugOptModVoltageStatusTrap NOTIFICATION-TYPE
        OBJECTS      { rcPortIndex, rcPlugOptModVoltageStatus }
        STATUS       current
        DESCRIPTION "Used to trap changes in the voltage level"
        ::= { rcTrapsMib 90 }

rcPlugOptModBiasStatusTrap NOTIFICATION-TYPE
        OBJECTS      { rcPortIndex, rcPlugOptModBiasStatus }
        STATUS       current
        DESCRIPTION "Used to trap changes in the laser bias status"
        ::= { rcTrapsMib 91 }

rcPlugOptModTxPowerStatusTrap NOTIFICATION-TYPE
        OBJECTS      { rcPortIndex, rcPlugOptModTxPowerStatus }
        STATUS       current
        DESCRIPTION "Used to trap changes in the transmit power status"
        ::= { rcTrapsMib 92 }

rcPlugOptModRxPowerStatusTrap NOTIFICATION-TYPE
        OBJECTS      { rcPortIndex, rcPlugOptModRxPowerStatus}
        STATUS       current
        DESCRIPTION "Used to trap changes in the received power status"
        ::= { rcTrapsMib 93 }

rcPlugOptModAux1StatusTrap NOTIFICATION-TYPE
        OBJECTS      { rcPortIndex,
		       rcPlugOptModAux1Monitoring,
		       rcPlugOptModAux1Status }
        STATUS       current
        DESCRIPTION "Used to trap changes in the Aux1 status"
        ::= { rcTrapsMib 94 }

rcPlugOptModAux2StatusTrap NOTIFICATION-TYPE
        OBJECTS      { rcPortIndex,
		       rcPlugOptModAux2Monitoring,
		       rcPlugOptModAux2Status }
        STATUS       current
        DESCRIPTION "Used to trap changes in the Aux2 status"
        ::= { rcTrapsMib 95 }

rcnCfmTrunkGroupDownTrap  NOTIFICATION-TYPE
        OBJECTS       { rcTlsTdiEndptTrunkGroup, 
                        rcCfmTrunkGroupProtected,
                        rcCfmTrunkGroupPrimaryTrunk}
        STATUS        current
        DESCRIPTION   "A TrunkGroupCcm trap signifies that two trunks in the
                       trunk group are not operational, This trap is replaced by
		       rcnCfmTrunkGroupDownExpandedTrap (156) in release 4.2 onwards"
        ::= { rcTrapsMib 96 }

rcnCfmTrunkGroupLostProtectionTrap  NOTIFICATION-TYPE
        OBJECTS       { rcTlsTdiEndptTrunkGroup, 
                        rcCfmTrunkGroupPrimaryTrunk,
                        rcCfmTrunkGroupSecondaryTrunk}
        STATUS        current
        DESCRIPTION   "A TrunkGroupCcm trap signifies that the
                       active trunk has been changed. This trap is replaced by
		       rcnCfmTrunkGroupLostProtectionExpandedTrap (153) in release 4.2 onwards"
        ::= { rcTrapsMib 97 }

rcnCfmPortMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcPortIndex,
	                rcVlanId,
                        rcCfmMepCcmIndication}
        STATUS        current
        DESCRIPTION   "A CfmPortMepCcm trap signifies that the
                       CCM operational state has been changed
                       for a MEP configured on a port. This trap is replaced by
		       rcnCfmPortMepCcmExpandedTrap (127) in release 4.2 onwards"
        ::= { rcTrapsMib 98 }

rcnCfmVlanPortMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcPortIndex,
	                rcVlanId,
                        rcCfmMepCcmIndication}
        STATUS        current
        DESCRIPTION   "A CfmVlanPortMepCcm trap signifies that the
                       CCM operational state has been changed
                       for a MEP configured on a vlan. This trap is replaced by
		       rcnCfmVlanPortMepCcmExpandedTrap (128) in release 4.2 onwards"
        ::= { rcTrapsMib 99 }

rcnCfmEndptMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcIsidBackboneVlan,
			rcPortIndex,
                        rcCfmMepCcmIndication}
        STATUS        current
        DESCRIPTION   "A CfmEndptMepCcm trap signifies that the
                       CCM operational state has been changed
                       for a MEP configured on an endpoint. it is not being 
		       used in release 4.2"
        ::= { rcTrapsMib 100 }
		  
rcnCfmEndptClientMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcPortIndex,				
                        rcCfmMepCcmIndication}
        STATUS        current
        DESCRIPTION   "A CfmEndptClientMepCcmtrap signifies that the
                       CCM operational state has been changed
                       for a MEP. This trap is replaced by 
		       rcnCfmEndptClientMepCcmExpandedTrap (129) in release 4.2 onwards"
        ::= { rcTrapsMib 101 }
		  
rcnCfmEndptCvidClientMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcPortIndex,
			rcCfmCvid,				
                        rcCfmMepCcmIndication}
        STATUS        deprecated
        DESCRIPTION   "A CfmEndptCvidClientMepCcm trap signifies that the
                       CCM operational state has been changed for a MEP"
        ::= { rcTrapsMib 102 }

rcnCfmTrunkGroupNewActiveTrunkTrap  NOTIFICATION-TYPE
        OBJECTS       { rcTlsTdiEndptTrunkGroup, 
                        rcCfmTrunkGroupActiveTrunk,
                        rcCfmTrunkGroupIndication}
        STATUS        current
        DESCRIPTION   "A TrunkGroupCcm trap signifies that the
                       active trunk has been changed. This trap is replaced by
			rcnCfmTrunkGroupNewActiveTrunkExpandedTrap (155) in release 4.2 onwards"
        ::= { rcTrapsMib 103 }

rcTlsTdiWatermarkTrap  NOTIFICATION-TYPE
        OBJECTS       { rcTlsTdiId,
                        rcTlsSlot,
                        rcTlsEndptWatermarkIndication,
			rcTlsRmodLane}
        STATUS        current
        DESCRIPTION   "A Watermark trap signifies that the r-mod
                       Mac Table for a TDI/lane has reached its high
                       watermark or is already full"
        ::= { rcTrapsMib 104 }

rcTlsIsidWatermarkTrap  NOTIFICATION-TYPE
        OBJECTS       { rcTlsIsidId,
                        rcTlsSlot,
                        rcTlsEndptWatermarkIndication,
			rcTlsRmodLane}
        STATUS        current
        DESCRIPTION   "A Watermark trap signifies that the r-mod
                       Mac Table for an ISID/lane has reached its high
                       watermark or is already full"
        ::= { rcTrapsMib 105 }

rcnCfmTrunkMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmTrunkSourceMac,
			rcCfmTrapTrunkName,
			rcPortIndex,
	                rcVlanId,
                        rcCfmTrunkReverseVlanId,
                        rcCfmMepCcmIndication}
        STATUS        current
        DESCRIPTION   "A CfmTrunkMepCcm trap signifies that the
                       CCM operational state has been changed
                       for a MEP configured on a Trunk. This trap is replaced
		       by rcnCfmTrunkMepCcmExpandedTrap (158) in release 4.2 onwards"
        ::= { rcTrapsMib 106 }

rcnCfmTrunkGroupTrap  NOTIFICATION-TYPE
        OBJECTS       { rcTlsTdiEndptTrunkGroup, 
                        rcCfmTrunkGroupProtected,
                        rcCfmTrunkGroupPrimaryTrunk}
        STATUS        current
        DESCRIPTION   "A rcnCfmTrunkGroupTrap trap signifies that two trunks in the
                       trunk group are not operational or at least one trunk in the
                       trunk group comes back up. This trap is replaced by two new traps
		       rcnCfmTrunkGroupDownExpandedTrap(156) and 
		       rcnCfmTrunkGroupUpExpandedTrap (157) in release 4.2 onwards"
        ::= { rcTrapsMib 107 }

rcnCfmTrunkGroupRecoverProtectionTrap  NOTIFICATION-TYPE
        OBJECTS       { rcTlsTdiEndptTrunkGroup, 
                        rcCfmTrunkGroupPrimaryTrunk}
        STATUS        current
        DESCRIPTION   "A rcnCfmTrunkGroupRecoverProtectionTrap trap signifies 
                       that trunk group has recovered protection. This trap is replaced by
                       rcnCfmTrunkGroupRecoverProtectionExpandedTrap (154) in release 4.2 onwards"
        ::= { rcTrapsMib 108 }

rcInvalidEsuModIdTrap NOTIFICATION-TYPE
        OBJECTS       { rcBanRingTopoRbsId,
                        rcBanRingTopoRbsMac }
        STATUS        current
        DESCRIPTION   "A rcEsuInvalidModIdTrap trap signifies that invalid ModID is
                       configured on the ESU"

        ::= { rcTrapsMib 109 } 
-- OID from 88 to 109 have been reseved for OE feature Trap definition,
-- Please used 110 and up. Thanks.

rcnMaxRouteWarnClear NOTIFICATION-TYPE
        OBJECTS      { rcVrfName }
        STATUS        current
        DESCRIPTION  "A rcnMaxRouteWarnClear trap signifies that
                     the number of routes in the routing table of
                     the Virtual Router has droped below its
                     warning threshold."
        ::= { rcTrapsMib 110 }

 rcnMaxRouteWarnSet NOTIFICATION-TYPE
        OBJECTS      { rcVrfName }
        STATUS        current
        DESCRIPTION  "A rcnMaxRouteWarnSet trap signifies that
                     the given Virtual Routers routing table is 
                     reaching its maximum size. Action should be
                     taken to prevent this"
        ::= { rcTrapsMib 111 }

rcnMaxRouteDropClear NOTIFICATION-TYPE
        OBJECTS      { rcVrfName }
        STATUS        current
        DESCRIPTION  "A rcnMaxRouteDropClear signifies that
                     the given Virtual Routers routing table is 
                     no longer dropping new routes as it is below
                     its maximum size."
        ::= { rcTrapsMib 112 }

rcnMaxRouteDropSet NOTIFICATION-TYPE
        OBJECTS      { rcVrfName }
        STATUS        current
        DESCRIPTION  "A rcnMaxRouteDropSet trap signifies that
                     the given Virtual Routers routing table has
                     reached its maximum size, and is now dropping
                     all new non static routes."
        ::= { rcTrapsMib 113 }

rcnTrialPeriodExpired NOTIFICATION-TYPE
        STATUS        current
        DESCRIPTION   "Trial period expired."
        ::= { rcTrapsMib 114 }

rcnVrfForwardingEnabled NOTIFICATION-TYPE
        OBJECTS      { rcVrfName }
        STATUS        current
        DESCRIPTION  "A rcnVrfForwardingEnable trap signifies that
                     the given Virtual Router's route forwarding  
                     is enabled. The VRF is functioning normally."
        ::= { rcTrapsMib 115 }
        
rcnVrfForwardingDisabled NOTIFICATION-TYPE
        OBJECTS      { rcVrfName }
        STATUS        current
        DESCRIPTION  "A rcnVrfForwardingDisabletrap signifies that
                     the given Virtual Router's route forwarding
                     is disabled. The VRF is no longer forwarding
                     routes."
        ::= { rcTrapsMib 116 }

rcnMstpNewCistRoot NOTIFICATION-TYPE
        OBJECTS       { rcStgBridgeAddress }
        STATUS        current
        DESCRIPTION   "A rcMstpNewCistRoottrap signifies that the
                      SNMPv2 entity, acting in an agent role, has
                      detected the Multiple Spanning Tree Protocol has
                      declared the device to be the new root of the common
                      internal spanning tree."
        ::= { rcTrapsMib 117 }


rcnMstpNewMstiRoot NOTIFICATION-TYPE
        OBJECTS       { rcStgBridgeAddress, rcStgId }
        STATUS        current
        DESCRIPTION   "A rcMstpNewMstiRoot signifies that the
                      SNMPv2 entity, acting in an agent role, has
                      detected the Multiple Spanning Tree Protocol has
                      declared the device to be the new root of the
                      spanning tree instance."
        ::= { rcTrapsMib 118 }

rcnMstpNewCistRegionalRoot NOTIFICATION-TYPE
        OBJECTS       { rcStgBridgeAddress }
        STATUS        current
        DESCRIPTION   "A rcMstpNewCistRegionalRoottrap signifies that the
                      SNMPv2 entity, acting in an agent role, has
                      detected the Multiple Spanning Tree Protocol has
                      declared the device to be the new regional root of
                      the common internal spanning tree."
        ::= { rcTrapsMib 119 }

rcnRstpNewRoot NOTIFICATION-TYPE
        OBJECTS       { rcStgBridgeAddress }
        STATUS        current
        DESCRIPTION   "A rcRstpNewRoot signifies that the SNMPv2 entity,
		      acting in an agent role, has detected the
		      Rapid Spanning Tree Protocol has declared the device
		      to be the new root of the spanning tree."
        ::= { rcTrapsMib 120 }
        
rcnIgmpNewQuerierOnIf NOTIFICATION-TYPE
        OBJECTS       { rcIgmpInterfaceIfIndex,
                        rcIgmpInterfaceQuerier }
        STATUS        current
        DESCRIPTION   "An igmpNewQuerier trap signifies that a new
                       querier has come up on an interface."
        ::= { rcTrapsMib 121 }

rcnIgmpQuerierChanged NOTIFICATION-TYPE
        OBJECTS       { rcIgmpInterfaceIfIndex,
                        rcIgmpInterfaceExtnNewQuerier,
                        rcIgmpInterfaceQuerier }
        STATUS        current
        DESCRIPTION   "An rcIgmpQuerierChange trap signifies that
                       the querier has changed."
        ::= { rcTrapsMib 122 }

rcnDuplexMismatch NOTIFICATION-TYPE
        OBJECTS       { rcPortIndex,lldpRemPortIdSubtype,lldpRemPortId }
        STATUS        current
        DESCRIPTION   "A rcnDuplexMismatch trap signifies that
                       a LLDP Neighbor Port's Duplex/Speed mismatches
                       with local port"
        ::= { rcTrapsMib  123 }

rcnRsmltEdgePeerModified NOTIFICATION-TYPE
        OBJECTS      { rcVlanName }
        STATUS       current
        DESCRIPTION  "A rcnRsmltEdgePeerModified signifies that 
                     the RSMLT Peer address is different from
                     that of the stored address. Save config is
                     necessary if EdgeSupport has to use this info
                     on next reboot." 
        ::= { rcTrapsMib 124 }

rcn2kLinkDownTrap  NOTIFICATION-TYPE
    OBJECTS { rcPortIndex, 
	      ifAdminStatus, 
	      ifOperStatus, 
              rcPortUserLabel1, 
              rcPortUserLabel2  }
    STATUS  current
    DESCRIPTION
            "A linkDown trap signifies that the SNMP entity, acting in
            an agent role, has detected that the ifOperStatus object for
            one of its communication links is about to enter the down
            state from some other state (but not from the notPresent
            state).  This other state is indicated by the included value
            of ifOperStatus."
    ::= { rcTrapsMib 125 }
 
rcn2kLinkUpTrap NOTIFICATION-TYPE
    OBJECTS { rcPortIndex, 
	      ifAdminStatus, 
	      ifOperStatus, 
              rcPortUserLabel1, 
              rcPortUserLabel2  }
    STATUS  current
    DESCRIPTION
            "A linkUp trap signifies that the SNMP entity, acting in an
            agent role, has detected that the ifOperStatus object for
            one of its communication links left the down state and
            transitioned into some other state (but not into the
            notPresent state).  This other state is indicated by the
            included value of ifOperStatus."
    ::= { rcTrapsMib 126  }

rcnCfmPortMepCcmExpandedTrap  NOTIFICATION-TYPE
        OBJECTS       { rcCfmMaintenanceEndPointDomainName,  
                        rcCfmMaintenanceEndPointAssociationName,
			rcCfmRemoteMepId,	
			rcCfmLocalMepId,
                        rcCfmRemoteMacAddr,
			rcPortIndex,
	                rcVlanId,
                        rcCfmMepCcmIndication,
                        rcPortUserLabel1,
                        rcPortUserLabel2,
			rcCfmDirection}
        STATUS        current
        DESCRIPTION   "A CfmPortMepCcm trap signifies that the
                       CCM operational state has been changed
                       for a MEP configured on a port.. If no
		       UserLabes are configured for the port, 
		       a NULL string will be included.This is a set and clear trap. 
		       The clearing is indicated by the rcCfmMepCcmIndication field.
		       This trap replaces the old trap rcnCfmPortMepCcmTrap(98) in release 4.2"
        ::= { rcTrapsMib 127 }

rcnCfmVlanPortMepCcmExpandedTrap  NOTIFICATION-TYPE
        OBJECTS       { rcCfmMaintenanceEndPointDomainName,  
                        rcCfmMaintenanceEndPointAssociationName,
			rcCfmRemoteMepId,	
			rcCfmLocalMepId,
                        rcCfmRemoteMacAddr,
			rcPortIndex,
	                rcVlanId,
                        rcCfmMepCcmIndication,
                        rcPortUserLabel1,
                        rcPortUserLabel2,
			rcCfmDirection}
        STATUS        current
        DESCRIPTION   "A CfmVlanPortMepCcm trap signifies that the
                       CCM operational state has been changed
                       for a MEP configured on a vlan.The UserLabels are
                       copied from the UserLabel field of the Vlan.
		       This is a set and clear trap. The clearing is indicated 
                       by the rcCfmMepCcmIndication field.  This trap replaces the
		       old trap rcnCfmVlanPortMepCcmTrap (99) in release 4.2"
        ::= { rcTrapsMib 128 }
		  
rcnCfmEndptClientMepCcmExpandedTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcPortIndex,				
                        rcCfmMepCcmIndication,
                        rcIsidEndptUserLabel1,
                        rcIsidEndptUserLabel2,
			rcCfmDirection}
        STATUS        current
        DESCRIPTION   "A CfmEndptClientMepCcmtrap signifies that the
                       CCM operational state has been changed
                       for a MEP. UserLabels are
                       copied from the UserLabel1 field of the EndPoint
		       This is a set and clear trap. The clearing is indicated 
                       by the rcCfmMepCcmIndication field. This trap replaces the old 
	               trap rcnCfmEndptCvidClientMepCcmTrap(101) in release 4.2 "
        ::= { rcTrapsMib 129 }
		  
rcnPbtUnknownDiscardTrap  NOTIFICATION-TYPE
        OBJECTS       { rc2kChassisBaseMacAddr,
			rcCfmRemoteMacAddr,
			rcCfmTrunkSourceMac,
			rcVlanId,
			rcPortIndex,
                        rc2kChassisUserLabel1 }
        STATUS        current
        DESCRIPTION   "The number of UnknownMac Discard exceeded the threshold.
                       Make sure that the FDB entry exists for specified vlan
		       and that the port is a member of the vlan. 
			The chassis Mac address is given in  
		       rc2kChassisBaseMacAddr which identifies the chassis "
        ::= { rcTrapsMib 130 }


rcnPbtUnknownDiscardClearTrap  NOTIFICATION-TYPE
        OBJECTS       { rc2kChassisBaseMacAddr,
                        rc2kChassisUserLabel1 }
        STATUS        current
        DESCRIPTION   "The number of UnknownMac Discard exceeded the threshold.
                       Make sure that the FDB entry exists for specified vlan
		       and that the port is a member of the vlan. 
			The chassis Mac address is given in  
		       rc2kChassisBaseMacAddr which identifies the chassis "
        ::= { rcTrapsMib 131 }



rcn2kQosDropTrap  NOTIFICATION-TYPE
        OBJECTS       { rc2kChassisBaseMacAddr,
			rc2kQosQosRow,
			rcPortIndex,
			rc2kQosQosDropThresholdPercentage,
			rc2kQosQosDropActualPercentage,
                        rc2kChassisUserLabel1}
        STATUS        current
        DESCRIPTION   "Drop count of packets for a specific QoS level has exceeded  the
		       configured threshold "
        ::= { rcTrapsMib 132}

rcn2kQosDropClearTrap  NOTIFICATION-TYPE
        OBJECTS       { rc2kChassisBaseMacAddr,
			rc2kQosQosRow,
			rcPortIndex,
			rc2kQosQosDropThresholdPercentage,
			rc2kQosQosDropActualPercentage,
                        rc2kChassisUserLabel1}
        STATUS        current
        DESCRIPTION   "Drop count of packets for a specific QoS level is with in the limits. Clears
			rcTrapsMib 132." 
        ::= { rcTrapsMib 133}

	  
rcnCfmTrunkFlrNearEndTrap NOTIFICATION-TYPE
	OBJECTS	      { rcCfmMaintenanceEndPointDomainName,  
                        rcCfmMaintenanceEndPointAssociationName,
			rcCfmRemoteMepId,	
			rcCfmLocalMepId,
			rcCfmRemoteMacAddr,
			rcCfmTrunkSourceMac,
			rcCfmTrapTrunkName,
			rcPortIndex,
	                rcVlanId,
                        rcCfmTrunkReverseVlanId,
			rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcCfmTrunkUserLabel1,
			rcCfmTrunkUserLabel2
		     }
	STATUS	     current
	DESCRIPTION   "A CfmTrunkFlrNearEnd trap signifies that the 
		      Frame Loss Ratio over Short Period threshold has
		      been crossed for ingress data frames."
	::= { rcTrapsMib 134 }

rcnCfmTrunkFlrFarEndTrap NOTIFICATION-TYPE
	OBJECTS	      { rcCfmMaintenanceEndPointDomainName,  
                        rcCfmMaintenanceEndPointAssociationName,
			rcCfmRemoteMepId,	
			rcCfmLocalMepId,
			rcCfmRemoteMacAddr,
			rcCfmTrunkSourceMac,
			rcCfmTrapTrunkName,
			rcPortIndex,
	                rcVlanId,
                        rcCfmTrunkReverseVlanId,
			rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcCfmTrunkUserLabel1,
			rcCfmTrunkUserLabel2
		      }
	STATUS	      current
	DESCRIPTION   "A CfmTrunkFlrFarEnd trap signifies that the
		       Frame Loss Ratio over Short Period threshold has
		       been crossed for egress data frames."
	::= { rcTrapsMib 135}

rcnCfmTrunkFdTrap NOTIFICATION-TYPE
	OBJECTS	      { rcCfmMaintenanceEndPointDomainName,  
                        rcCfmMaintenanceEndPointAssociationName,
			rcCfmRemoteMepId,	
			rcCfmLocalMepId,
			rcCfmRemoteMacAddr,
			rcCfmTrunkSourceMac,
			rcCfmTrapTrunkName,
			rcPortIndex,
	                rcVlanId,
                        rcCfmTrunkReverseVlanId,
			rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcCfmFdTarget,
			rcCfmFdAverage,
			rcCfmTrunkUserLabel1,
			rcCfmTrunkUserLabel2
		      }
	STATUS	      current
	DESCRIPTION   "A CfmTrunkFd trap signifies that the
		       Frame Delay over Short Period threshold has
		       been crossed."
	::= { rcTrapsMib 136 }

rcnCfmTrunkFdvTrap NOTIFICATION-TYPE
	OBJECTS	      { rcCfmMaintenanceEndPointDomainName,  
                        rcCfmMaintenanceEndPointAssociationName,
			rcCfmRemoteMepId,	
			rcCfmLocalMepId,
			rcCfmRemoteMacAddr,
			rcCfmTrunkSourceMac,
			rcCfmTrapTrunkName,
			rcPortIndex,
	                rcVlanId,
                        rcCfmTrunkReverseVlanId,
			rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcCfmFdvTarget,
			rcCfmFdvAverage,
			rcCfmTrunkUserLabel1,
			rcCfmTrunkUserLabel2
		      }
	STATUS	      current
	DESCRIPTION   "A cfmTrunkFdv trap signifies that the
		       Frame Delay Variation over Short Period
		       threshold has been crossed."
	::= { rcTrapsMib 137 }

rcnCfmEndptClientFdTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcPortIndex,
			rcCfmMonitorCosPriority,				
                        rcCfmThresholdIndication,
			rcCfmActualPercentage,
			rcCfmActualSubPercentage,
			rcCfmAlarmThreshold,
			rcCfmAlarmSubThreshold,
			rcCfmClearThreshold,
			rcCfmClearSubThreshold,
			rcCfmFdTarget,
			rcCfmFdAverage,
			rcIsidEndptUserLabel1,
			rcIsidEndptUserLabel2
		      }

        STATUS        current
        DESCRIPTION   "A cfmEndptClientFdTrap signifies that the
                       Frame Delay over Short Period threshold
		       has been crossed.
		       
		      CCM origin:    
		   	rcCfmMaintenanceEndPointDomainName, 
			rcCfmMaintenanceEndPointAssociationName, 
    			rcCfmRemoteMepId, 
			rcCfmLocalMepId
		      L1-L3 origin: 
 			rcCfmRemoteMacAddr, rcCfmIsidId, 
			rcIsidBackboneVlan, rcPortIndex
		      Customer Label: 
			rcCfmUserLabel1, rcCfmUserLabel2
		      FD info:
			rcCfmThresholdIndication,
			rcCfmActualPercentage,rcCfmActualSubPercentage,
			rcCfmAlarmThreshold, rcCfmAlarmSubThreshold,
			rcCfmClearThreshold, rcCfmClearSubThreshold,
			rcCfmFdTarget, rcCfmFdAverage"
        ::= { rcTrapsMib 138 }
		  
rcnCfmEndptClientFdvTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcPortIndex,
			rcCfmMonitorCosPriority,				
                        rcCfmThresholdIndication,
			rcCfmActualPercentage,
			rcCfmActualSubPercentage,
			rcCfmAlarmThreshold,
			rcCfmAlarmSubThreshold,
			rcCfmClearThreshold,
			rcCfmClearSubThreshold,
			rcCfmFdvTarget,
			rcCfmFdvAverage,
			rcIsidEndptUserLabel1,
			rcIsidEndptUserLabel2
		      }

        STATUS        current
        DESCRIPTION   "A cfmEndptClientFdvTrap signifies that the
                       Frame Delay Variation over Short Period 
		       threshold has been crossed.

		       CCM origin:    
		   	rcCfmMaintenanceEndPointDomainName, 
			rcCfmMaintenanceEndPointAssociationName, 
    			rcCfmRemoteMepId, 
			rcCfmLocalMepId
		      L1-L3 origin: 
 			rcCfmRemoteMacAddr, rcCfmIsidId, 
			rcIsidBackboneVlan, rcPortIndex
		      Customer Label: 
			rcCfmUserLabel1, rcCfmUserLabel2
		      FD info:
			rcCfmThresholdIndication,
			rcCfmActualPercentage,rcCfmActualSubPercentage,
			rcCfmAlarmThreshold, rcCfmAlarmSubThreshold,
			rcCfmClearThreshold, rcCfmClearSubThreshold,
			rcCfmFdvTarget, rcCfmFdvAverage"
        ::= { rcTrapsMib 139 }

rcnCfmMltEndptClientMepCcmTrap 	NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcPortMltId,		
                        rcCfmMepCcmIndication,
			rcIsidEndptUserLabel1,
			rcIsidEndptUserLabel2,
			rcCfmDirection
	              }

        STATUS        current
        DESCRIPTION   "A CfmMltEndptClientMepCcm trap signifies that the
                       CCM operational state has been changed for a MLT MEP."
	::= {rcTrapsMib 140 }

rcnCfmVlanMltMepCcmTrap NOTIFICATION-TYPE
        OBJECTS       { rcCfmMaintenanceEndPointDomainName,  
                        rcCfmMaintenanceEndPointAssociationName,
			rcCfmRemoteMepId,	
			rcCfmLocalMepId,
                        rcCfmRemoteMacAddr,
			rcPortMltId,
			rcVlanId,				
                        rcCfmMepCcmIndication,
			rcPortUserLabel1,
			rcPortUserLabel2,
			rcCfmDirection
	              }

        STATUS        current
        DESCRIPTION   "A CfmVlanMltMepCcmTrap trap signifies that the
                       CCM operational state has been changed for a MLT MEP
		       associated with a vlan"
        ::= { rcTrapsMib 141 }

rcnCfmRingEndptClientMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcIsidEndptRingId,
			rcIsidEndptModId,
			rcIsidEndptEsuPort,				
                        rcCfmMepCcmIndication,
			rcIsidEndptUserLabel1,
			rcIsidEndptUserLabel2,
			rcCfmDirection
		      }

        STATUS        current
        DESCRIPTION   "A CfmRingEndptClientMepCcmtrap signifies that the
                       CCM operational state has been changed
                       for a Ring MEP"
        ::= { rcTrapsMib 142 }

rcn2kGbicRemovedTrap   NOTIFICATION-TYPE
        OBJECTS       { rc2kCardIndex,
                        rcPortIndex,
			rcPortUserLabel1,
			rcPortUserLabel2,	
	 		rc2kChassisUserLabel1 }
        STATUS        current
        DESCRIPTION   "A rcGbicRemoved trap signifies that the SNMPv2 entity,
                     acting in an agent role, has detected that the
                     an Xfp/Sfp is removed from the specified slot and port."
        ::= { rcTrapsMib 143 }

rcn2kGbicInsertedTrap  NOTIFICATION-TYPE
        OBJECTS      { rc2kCardIndex,
                       rcPortIndex,
			rcPortUserLabel1,
			rcPortUserLabel2,
		       rc2kChassisUserLabel1 }
        STATUS       current
        DESCRIPTION  "A rcGbicInserted trap signifies that the SNMPv2 entity,
                     acting in an agent role, has detected that the
                     an Xfp/Sfp is inserted to the specified slot and port. "
        ::= { rcTrapsMib 144 }

rcn2kCardDownExpandedTrap NOTIFICATION-TYPE
        OBJECTS      { rc2kCardIndex,
                       rc2kCardFrontAdminStatus,
                       rc2kCardFrontOperStatus,
		                 rc2kChassisUserLabel1 }
        STATUS       current
        DESCRIPTION  "A rcCardDown trap signifies that the SNMPv2 entity,
                     acting in an agent role, has detected that the
                     rcCardOperStatus object for one of its cards
                     is about to transition into the down state."
        ::= { rcTrapsMib 145 }


rcn2kCardUpExpandedTrap  NOTIFICATION-TYPE
        OBJECTS       { rc2kCardIndex,
                        rc2kCardFrontAdminStatus,
                        rc2kCardFrontOperStatus,
	 		               rc2kChassisUserLabel1 }
        STATUS        current
        DESCRIPTION   "A rcCardUp trap signifies that the SNMPv2 entity,
                      acting in an agent role, has detected that the
                      rcCardOperStatus object for one of its cards
                      is about to transition into the up state.
		      Clears rcn2kCardDownExpanded."
        ::= { rcTrapsMib 146 }

rcnCSUStartTrap NOTIFICATION-TYPE
	OBJECTS		{ rcCsuGlobalStartUpMode }
	STATUS		current
	DESCRIPTION	"A rcCSUStartTrap trap signifies that 
                         the controlled software upgrade has started 
                         in the specified mode"

	::= { rcTrapsMib 147 }

rcnCSUEndTrap NOTIFICATION-TYPE
	OBJECTS		{ rcCsuGlobalStartUpMode }
	STATUS		current
	DESCRIPTION	"A rcCSUEndTrap trap signifies that the 
                         controlled software upgrade has ended in 
                         the specified mode"

	::= { rcTrapsMib 148 }

rcnCSUCardResetStartTrap NOTIFICATION-TYPE
	OBJECTS		{ rcCsuInfoTypeOfCardDesc, rc2kCardIndex }
	STATUS		current
	DESCRIPTION	"A rcCSUCardResetStartTrap trap signifies that 
                         the card in the specified slot reset process 
                         has started as part of the CSU"

	::= { rcTrapsMib 149 }

rcnCSUCardResetEndTrap NOTIFICATION-TYPE
	OBJECTS		{ rcCsuInfoTypeOfCardDesc, rc2kCardIndex }
	STATUS		current
	DESCRIPTION	"A rcCSUCardResetEndTrap trap signifies that 
                         the card in the specified slot reset process 
                         has ended as part of the CSU"

	::= { rcTrapsMib 150 }

rcnCSUInProgressTrap NOTIFICATION-TYPE
	STATUS		current
	DESCRIPTION	"A rcCSUInProgressTrap signifies that the CSU 
                         in progress and some cards need to be upgraded"

	::= { rcTrapsMib 151 }

rcnTlsIpServiceWatermarkTrap  NOTIFICATION-TYPE
        OBJECTS       { rcTlsIpCustIpVlan,
                        rcTlsIpCustIpWatermarkIndication,
                        rcTlsRmodLane}
        STATUS        current
        DESCRIPTION   "A Watermark trap signifies that the
                       Ip Table for the Ip Service (Cust Ip)
                       has reached its high watermark or already full"
        ::= { rcTrapsMib 152 }

rcnCfmTrunkGroupLostProtectionExpandedTrap  NOTIFICATION-TYPE
        OBJECTS       { rcCfmTrapTrunkGroupName, 
                        rcCfmTrunkGroupPrimaryTrunk,
                        rcCfmTrunkGroupSecondaryTrunk,
		        rcCfmTrapTrunkName,
			rcCfmTrunkGroupUserLabel1,
			rcCfmTrunkGroupUserLabel2}
        STATUS        current
        DESCRIPTION   "A TrunkGroupCcm trap signifies that on of the trunks in
                       the truck group has failed and so the path is not protected 
		       anymore. The trap information includes the names of primary trunk
	               and the secondary trunk and the name of the trunk that filed. 
		       In release 4.2, this repalcess the old trap 
		       rcnCfmTrunkGroupLostProtectionTrap (97)"
        ::= { rcTrapsMib 153 }
 	  
rcnCfmTrunkGroupRecoverProtectionExpandedTrap  NOTIFICATION-TYPE
        OBJECTS       {  rcCfmTrapTrunkGroupName,
                        rcCfmTrunkGroupPrimaryTrunk,
                        rcCfmTrunkGroupSecondaryTrunk,
		        rcCfmTrapTrunkName,
			rcCfmTrunkGroupUserLabel1,
			rcCfmTrunkGroupUserLabel2 }
        STATUS        current
        DESCRIPTION   "A rcnCfmTrunkGroupRecoverProtectionTrap trap signifies 
                       that trunk group has recovered protection. Trunk that was
                       don earlier as reported in trap rcnTrapsMib 114
	               (rcnCfmTrunkGroupLostProtectionExpandedTrap) is up.The trap 
		  	information includes the names of primary trunk
	               	and the secondary trunk and the name of the trunk that came up.
			This trap replaces the old trap rcnCfmTrunkGroupRecoverProtectionTrap(108)
		        in release 4.2"
        ::= { rcTrapsMib 154 }

rcnCfmTrunkGroupNewActiveTrunkExpandedTrap  NOTIFICATION-TYPE
        OBJECTS       {  rcCfmTrapTrunkGroupName,
			rcCfmTrunkGroupPrimaryTrunk,
                        rcCfmTrunkGroupSecondaryTrunk,
		        rcCfmTrapTrunkName,
			rcCfmTrunkGroupUserLabel1,
			rcCfmTrunkGroupUserLabel2 } 
                        
        STATUS        current
        DESCRIPTION   "A TrunkGroupCcm trap signifies that the
                       active trunk has been changed. The user has manually switched
                       the active trunk. The trap gives the name of both trunks in the 
                       group and the name on the user selected active trunk. This trap replaces 
		       the old trap rcnCfmTrunkGroupNewActiveTrunkTrap (103) in release 4.2 "
                      
        ::= { rcTrapsMib 155 }

rcnCfmTrunkGroupDownExpandedTrap  NOTIFICATION-TYPE
        OBJECTS       { rcCfmTrapTrunkGroupName,
 			rcCfmTrunkGroupPrimaryTrunk,
                        rcCfmTrunkGroupSecondaryTrunk,
		        rcCfmTrapTrunkName,
			rcCfmTrunkGroupUserLabel1,
			rcCfmTrunkGroupUserLabel2 }
        STATUS        current
        DESCRIPTION   "A rcnCfmTrunkGroupTrap trap signifies that both the trunks in the
                       trunk group are not operational. One trunk was already down as 
                       reported by rcnCfmTrunkGroupLostProtectionTrap (rcTrapsMib 114). 
		       Now the scecod trunk has done down.
                       Tne trap contains the names of both trunks and the neme of the
		       trunk that just went down.
		       The trap contains the names of both trunks and the name of the
		       trunk that just went down.This condition will result in traffic 
		       loss and should be corrected. It repleaces the old trap 
		       rcnCfmTrunkGroupDownTrap (96) in release 4.2"            
        ::= { rcTrapsMib 156 }

rcnCfmTrunkGroupUpExpandedTrap  NOTIFICATION-TYPE
        OBJECTS       { rcCfmTrapTrunkGroupName,
 			rcCfmTrunkGroupPrimaryTrunk,
                        rcCfmTrunkGroupSecondaryTrunk,
		        rcCfmTrapTrunkName,
			rcCfmTrunkGroupUserLabel1,
			rcCfmTrunkGroupUserLabel2
			 }
        STATUS        current
        DESCRIPTION   "A rcnCfmTrunkGroupTrap trap signifies that one of the trunks
                       in the trunk group is operational. Earlier both trunks tn the
                       trunk group was down. This clears the condition as reported
                       in rcTrapsMib 117 (rcnCfmTrunkGroupDownExpandedTrap). 
                       Tne trap contains the names of both trunks and the neme of the
		       trunk that just became operational."
            
        ::= { rcTrapsMib 157 }

rcnCfmTrunkMepCcmExpandedTrap   NOTIFICATION-TYPE
        OBJECTS       { rcCfmMaintenanceEndPointDomainName,  
                        rcCfmMaintenanceEndPointAssociationName,
			rcCfmRemoteMepId,	
			rcCfmLocalMepId,
                        rcCfmRemoteMacAddr,
			rcCfmTrunkSourceMac,
			rcCfmTrapTrunkName,
			rcPortIndex,
	                rcVlanId,
                        rcCfmTrunkReverseVlanId,
                        rcCfmMepCcmIndication,
			rcCfmTrunkUserLabel1,
			rcCfmTrunkUserLabel2,
			rcCfmDirection}
        STATUS        current
        DESCRIPTION   "A CfmTrunkMepCcmExp  trap signifies that the
                       CCM operational state has been changed
                       for a MEP configured on a Trunk. The rcCfmMepCcmIndication
                       will be set to 1 when the trunk is operational and set to 2
                       if the trunk is down. This trap replaces the old trap 
		       rcnCfmTrunkMepCcmTrap (106) in release 4.2"
        ::= { rcTrapsMib 158 }

rcnCfmStandEndptClientMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcPortIndex,
			rcIsidEndptModId,
			rcIsidEndptEsuPort,				
                        rcCfmMepCcmIndication,
			rcIsidEndptUserLabel1,
			rcIsidEndptUserLabel2,
			rcCfmDirection
		      }

        STATUS        current
        DESCRIPTION   "A CfmStandaloneEndptClientMepCcmtrap signifies that the
                       CCM operational state has been changed
                       for a Standalone-Esu MEP"
        ::= { rcTrapsMib 159 }

rcnMltLinkUp NOTIFICATION-TYPE
        OBJECTS       { rcMltId }
        STATUS        current
        DESCRIPTION   "A rcMltLinkUp trap signifies that the
                      MLT link is up."
        ::= { rcTrapsMib 160 }

rcnMltLinkDown NOTIFICATION-TYPE
        OBJECTS       { rcMltId }
        STATUS        current
        DESCRIPTION   "A rcMltLinkDown trap signifies that the
                      MLT link is down."
        ::= { rcTrapsMib 161 }

rcnLinkBadConnection NOTIFICATION-TYPE
        OBJECTS          { rcPortIndex }
        STATUS             current
        DESCRIPTION   "A rcnLinkBadConnection trap signifies that the
                       SNMPv2 entity, acting in an agent role, has
                       detected a bad fiber connection to the receiver
                       on the specified port."
        ::= { rcTrapsMib 162 }

rcnMcInRecMoreThanThreshold NOTIFICATION-TYPE
	STATUS             current
	DESCRIPTION    "An rcnMcInRecMoreThanThreshold signifies that 
			number of MC Ingress records has exceeded the 
		        configured ingress-threshold."
	::= { rcTrapsMib 163 }
 
rcnMcEgRecMoreThanThreshold NOTIFICATION-TYPE
	STATUS             current
	DESCRIPTION     "An rcnMcEgRecMoreThanThreshold signifies that
                         number of MC Egress records has exceeded the 
			 configured Egress-threshold."
	::= { rcTrapsMib 164 }

rcnTmuxParityError NOTIFICATION-TYPE
        OBJECTS { rc2kDeviceGlobalSlot }
        STATUS        current
        DESCRIPTION   "A rcnTmuxParityError trap identifies a problem
		       in the FAD/SWIP based on the number of parity errors."
        ::= { rcTrapsMib 165 }

rcnCfmDHRingEndptClientMepCcmTrap  NOTIFICATION-TYPE
        OBJECTS       { rcCfmMaintenanceEndPointDomainName,  
                        rcCfmMaintenanceEndPointAssociationName,
			rcCfmRemoteMepId,	
			rcCfmLocalMepId,
                        rcCfmRemoteMacAddr,
			rcCfmIsidId,
			rcCfmVid,
			rcIsidEndptRingId,
			rcIsidEndptModId,
			rcIsidEndptEsuPort,				
                        rcCfmMepCcmIndication,
			rcIsidEndptUserLabel1,
			rcIsidEndptUserLabel2,
			rcCfmDirection
		      }

        STATUS        current
        DESCRIPTION   "A CfmDHRingEndptClientMepCcmtrap signifies that the
                       CCM operational state has been changed
                       for a Dual-Home Ring MEP"
        ::= { rcTrapsMib 166 }
		  
rcnChasPowerSupplyNoRedundancy NOTIFICATION-TYPE
        STATUS        current
        DESCRIPTION  "A rcnChasPowerSupplyNoRedundancy signifies that
                     the chassis is running on power supply without 
                     redundancy."
        ::= { rcTrapsMib 167 }

rcnChasPowerSupplyRedundancy NOTIFICATION-TYPE
        STATUS        current
        DESCRIPTION  "A rcnChasPowerSupplyRedundancy signifies that
                     the chassis is running on power supply with 
                     redundancy."
        ::= { rcTrapsMib 168 }

rcnPortAdminStatusChangeTrap NOTIFICATION-TYPE
        OBJECTS       { rcPortIndex,
                        ifAdminStatus }
        STATUS         current
        DESCRIPTION   "In an event of admin status change from enable
                        to disable or vice-versa, this trap is sent 
                        to notify change in admin status" 
        ::= { rcTrapsMib 169 }

rcnSaveConfigFailTrap  NOTIFICATION-TYPE
        OBJECTS        { rcSysConfigFileName }
        STATUS           current
        DESCRIPTION     "A rcnSaveConfigFail trap signifies that the
                         runtime config save is unsuccessful on the 
                         switch" 
        ::= { rcTrapsMib 170 }

rcnLicenseTrialPeriodExpired NOTIFICATION-TYPE
        STATUS        current
        DESCRIPTION  "A rcnLicenseTrialPeriodExpired signifies that
                      Trial Period License has expired."
        ::= { rcTrapsMib 171 }
 
rcnLicenseTrialPeriodExpiry NOTIFICATION-TYPE
        OBJECTS      { rcSysLicenseTrialDaysLeft }
        STATUS        current
        DESCRIPTION  "A rcnLicenseTrialPeriodExpiry signifies
                      the time remaining before License Trial Period
                      expires in days."
        ::= { rcTrapsMib 172 }

rcnVrfUp NOTIFICATION-TYPE
        OBJECTS      { rcVrfName, rcVrfOperStatus }
        STATUS        current
        DESCRIPTION  "This notification is generated when the specified
                      VRF's operational status is toggled from down to up."
        ::= { rcTrapsMib 173 }

rcnVrfDown NOTIFICATION-TYPE
        OBJECTS      { rcVrfName, rcVrfOperStatus }
        STATUS        current
        DESCRIPTION  "This notification is generated when the specified
                      VRF's operational status is toggled from up to down."
        ::= { rcTrapsMib 174 }

rcnMrouteIngressThresholdExceeded NOTIFICATION-TYPE
        OBJECTS      { rcIpResourceUsageGlobalIngressRecInUse,
                       rcIpResourceUsageGlobalIngressThreshold }
        STATUS        current
        DESCRIPTION  "This notification is generated when the number of
                      mroute ingress records exceeds the ingress threshold."
        ::= { rcTrapsMib 175 }

rcnMrouteEgressThresholdExceeded NOTIFICATION-TYPE
        OBJECTS      { rcIpResourceUsageGlobalEgressRecInUse,
                       rcIpResourceUsageGlobalEgressThreshold }
        STATUS        current
        DESCRIPTION  "This notification is generated when the number of
                      mroute egress records exceeds the egress threshold."
        ::= { rcTrapsMib 176 }

rcnRemoteMirroringStatus  NOTIFICATION-TYPE
        OBJECTS       { rcPortRemoteMirroringIndex,
                        rcPortRemoteMirroringEnable,
                        rcPortRemoteMirroringMode }
        STATUS        current
        DESCRIPTION   " A rcRemoteMirroringStatus trap signifies whether
                       the remote mirroring is enabled or disabled on a particular port."
        ::= { rcTrapsMib 177 }

rcnMaxMrouteWarnSet NOTIFICATION-TYPE
        OBJECTS      { rcVrfName }
        STATUS        current
        DESCRIPTION  "A rcnMaxMrouteWarnSet trap signifies that
                     the given Virtual Routers multicast routing table is 
                     reaching its maximum size. Action should be
                     taken to prevent this"
        ::= { rcTrapsMib 178 }

rcnMaxMrouteDropSet NOTIFICATION-TYPE
        OBJECTS      { rcVrfName }
        STATUS        current
        DESCRIPTION  "A rcnMaxMrouteDropSet trap signifies that
                     the given Virtual Routers multicast routing table has 
                     reached its maximum size, and is now dropping all
                     new non static routes"
        ::= { rcTrapsMib 179 }

rcnMaxMrouteWarnClear NOTIFICATION-TYPE
        OBJECTS      { rcVrfName }
        STATUS        current
        DESCRIPTION  "A rcnMaxMrouteWarnClear trap signifies that
                     the number of routes in the multicast routing table of
                     the Virtual Router has dropped below its
                     warning threshold."
        ::= { rcTrapsMib 180 }

rcnMaxMrouteDropClear NOTIFICATION-TYPE
        OBJECTS      { rcVrfName }
        STATUS        current
        DESCRIPTION  "A rcnMaxMrouteDropClear trap signifies that
                     the given Virtual Routers multicast routing table is 
                     no longer dropping new routes as it is below
                     its maximum size."
        ::= { rcTrapsMib 181 }

rcnAggLinkStateChange NOTIFICATION-TYPE
        OBJECTS      {rcMltId, rcMltAggTrapEvent}
        STATUS        current
        DESCRIPTION   "The trap is generated when the operational state
                       of the LAG changes; it identifies three events:
                       local down, remote down, up."
        ::= { rcTrapsMib 182 }
        
rcnBfdSessExceedThreshold NOTIFICATION-TYPE
        OBJECTS      { rcBfdTmpSessDiscriminator,rcBfdTmpSessAddr }
        STATUS	     current
        DESCRIPTION  "A rcnBfdSessExceedThreshold signifies that 
                      the BFD session have exceed system limit and hence
                      creation of new session failed."
        ::= { rcTrapsMib 183 }

rcnBfdStatusChange NOTIFICATION-TYPE
        OBJECTS      { rcBfdTmpSessDiscriminator, rcBfdTmpSessRemoteDiscr, rcBfdTmpSessAddr, 
                       rcBfdTmpSessState, rcBfdTmpSessState }
        STATUS	     current
        DESCRIPTION  "A rcnBfdSessChange signifies that the status
                    of BFD session changed."
        ::= { rcTrapsMib 184 }

rcnChasPowerSupplyRunningLow NOTIFICATION-TYPE
        STATUS        current
        DESCRIPTION  "A rcnChasPowerSupplyRunningLow signifies that
                     the chassis is running on low power supply."
        ::= { rcTrapsMib 185 }

rcnCfmEndptClientFlrNearEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortIndex,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2
		     }
	STATUS	     current
	DESCRIPTION   "A rcnCfmEndptClientFlrNearEndTrap trap signifies that the 
		      Frame Loss Ratio over Short Period threshold has
		      been crossed for ingress data frames."
	::= { rcTrapsMib 186 } 

rcnCfmEndptClientFlrFarEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortIndex,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2 
		      }
	STATUS	      current
	DESCRIPTION   "A rcnCfmEndptClientFlrFarEndTrap trap signifies that the
		       Frame Loss Ratio over Short Period threshold has
		       been crossed for egress data frames."
	::= { rcTrapsMib 187 } 

rcnTosBufferLimitTrap NOTIFICATION-TYPE
        OBJECTS       { rcPortIndex, rcErrorText } 
        STATUS        current
        DESCRIPTION   "A TOS Buffer limit trap signifies that the
                       TOS Buffer value does not fall within the
                       permissible limit"
        ::= { rcTrapsMib 188 } 

rcnTosBufferClearTrap NOTIFICATION-TYPE
        OBJECTS       { rcPortIndex, rcErrorText }
        STATUS        current
        DESCRIPTION   "A TOS Buffer clear trap signifies that the
                       TOS Buffer corruption is now cleared" 
        ::= { rcTrapsMib 189 }

rcnChasCoolingInsufficientTrap  NOTIFICATION-TYPE
        STATUS        current
        DESCRIPTION   "A rcnChasCoolingInsufficientTrap trap signifies 
		       that the fan tray(s) is not providing sufficient 
		       cooling power for the chassis configuration and 
		       that a fan tray upgrade is recommended. This 
		       trap is cleared by rcnChasCoolingSufficientTrap."
        ::= { rcTrapsMib 190}

rcnChasCoolingSufficientTrap  NOTIFICATION-TYPE
        STATUS        current
        DESCRIPTION   "rcnChasCoolingSufficientTrap trap signifies 
		       that the fan tray(s) is now providing sufficient 
		       cooling power for the chassis. Clears 
		       rcnChasCoolingInsufficientTrap." 
        ::= { rcTrapsMib 191}

rcnIsisPlsbMetricMismatchTrap  NOTIFICATION-TYPE
        OBJECTS       { rcIsisLocalLspId,  
                        rcIsisLocall1Metric,
			rcIsisNgbLspId,	
			rcIsisNgbl1Metric,
                        rcIsisPlsbTrapType,
			rcIsisTrapIndicator,
                        rcIsisLocalHostName,
                        rcIsisNgbHostName}
        STATUS        current
        DESCRIPTION   "A PLSB ISIS trap signifies that a LSP with a different 
                       value of l1-metric is received"
        ::= { rcTrapsMib 192 }

rcnIsisPlsbDuplicateSysidTrap  NOTIFICATION-TYPE
        OBJECTS       { rcIsisLocalSysId,
                        rcIsisLocalInterface,                
                        rcIsisPlsbTrapType,
                        rcIsisTrapIndicator}
        STATUS        current
        DESCRIPTION   "A PLSB ISIS trap signifies that a Hello packet with a 
                       duplicate system-id is received"
        ::= { rcTrapsMib 193 }

rcnIsisPlsbLsdbUpdateTrap  NOTIFICATION-TYPE
        OBJECTS       { rcIsisPlsbTrapType}
        STATUS        current
        DESCRIPTION   "A PLSB ISIS trap signifies that LSDB information has 
                       changed"
        ::= { rcTrapsMib 194 }

rcnIsisPlsbDuplicateNicknameTrap  NOTIFICATION-TYPE
        OBJECTS       { rcIsisLocalNickname, 
                        rcIsisPlsbTrapType,
                        rcIsisNgbNickname, 
                        rcIsisTrapIndicator,
                        rcIsisNgbSysId}
        STATUS        current
        DESCRIPTION   "A PLSB ISIS trap signifies that a LSP with duplicate
                       nickname is received"
        ::= { rcTrapsMib 195 }

rcnChasFanCoolingLow NOTIFICATION-TYPE
        OBJECTS       { rcChasFanOperStatus, rcChasFanType,
                        rcErrorLevel, rcErrorText }       
        STATUS        current
        DESCRIPTION  "A rcnChasFanCoolingLow signifies that
                     the chassis is running on low fan cooling."
        ::= { rcTrapsMib 196 }

rcnFOQDropTrap  NOTIFICATION-TYPE
        OBJECTS       { rc2kCardIndex,
			rcTlsRmodLane,
			rc2kQosTotalDropReadings,
			rc2kQosDropReadings}
        STATUS        current
        DESCRIPTION   "A rcnFOQDropTrap signifies that there are FOQ Drops.
		      CardIndex indicates the slot number, RmodLane indicates 
		      the lane number, TotalDropReadings indicates the total 
		      count of drop samples and DropReadings indicates the 
		      drop samples observed within the drop-trap time interval."
        ::= { rcTrapsMib 197}

rcnFabricDropTrap  NOTIFICATION-TYPE
        OBJECTS       { rc2kCardIndex,
			rcTlsRmodLane,
			rc2kQosTotalDropReadings,
			rc2kQosDropReadings
			}
        STATUS        current
        DESCRIPTION   "A rcnFabricDropTrap signifies that there are Fabric Drops.
		      CardIndex indicates the slot number, RmodLane indicates 
		      the lane number, TotalDropReadings indicates the total 
		      count of drop samples and DropReadings indicates the 
		      drop samples observed within the drop-trap time interval."
        ::= { rcTrapsMib 198}

rcnRSlotFabricActiveTrap NOTIFICATION-TYPE
            OBJECTS        { rc2kCardIndex }
            STATUS          current
            DESCRIPTION "A rcnTripodSlotRStateActiveTrap signifies that Slot R mapped
                                   to Slot 5 or Slot 6."
            ::= { rcTrapsMib 199 }

rcnRSlotFabricInactiveTrap NOTIFICATION-TYPE
            OBJECTS       { rc2kCardIndex }
            STATUS          current
             DESCRIPTION "A rcnTripodSlotRStateInactiveTrap signifies that Slot R unmapped
                                    from Slot 5 or Slot 6."
            ::= { rcTrapsMib 200 }

rcnLockupDetected NOTIFICATION-TYPE
            OBJECTS      {rc2kDeviceGlobalSlot}
            STATUS        current
            DESCRIPTION   "A rcnLockupDetected trap identifies a lock-up in the specified 
  		 	   module and requests the user to take corrective action"
            ::= { rcTrapsMib 201 }

rcnMacResetForLockup NOTIFICATION-TYPE
            OBJECTS      {rc2kDeviceGlobalSlot}
            STATUS        current
            DESCRIPTION   "A rcnMacResetForLockup trap is sent when lock-up was detected in 
 	    		   a slot and a mac reset has been done as a corrective action." 
            ::= { rcTrapsMib 202 }

rcnModuleResetForLockup NOTIFICATION-TYPE
            OBJECTS      {rc2kDeviceGlobalSlot}
            STATUS        current
            DESCRIPTION   "A rcnModuleResetForLockup trap is sent when lock-up was detected in 
                 	   a slot and a module has been reset as a corrective action." 
            ::= { rcTrapsMib 203 }

rcnModuleFatalError NOTIFICATION-TYPE
            OBJECTS      {rc2kDeviceGlobalSlot}
            STATUS        current
            DESCRIPTION   "A rcnModuleFatalError trap is sent when a fatal error is detected in 
			   a module and the user has to take corrective action." 
            ::= { rcTrapsMib 204 }

rcnSmpFtpFail NOTIFICATION-TYPE
            STATUS       current
            DESCRIPTION  "A rcnSmpFtpFail trap signifies that Ftp/Tftp of a logfile
                          has failed in SMP (System Messaging Platform). Ftp of a
                          logfile fails when the configured remote server is not
                          reachable or remote server is not configured."
            ::= { rcTrapsMib 205 }
 
rcnSmpLogFileDeleted NOTIFICATION-TYPE
            STATUS       current
            DESCRIPTION  "A rcnSmpLogFileDeleted trap signifies that a logfile
                          has been deleted from PCMCIA. Deletion of a logfile happens
                          when either FTP of the logfile is successful or PCMCIA has
                          no space to create another logfile."
            ::= { rcTrapsMib 206 }

rcnUpgradeSuccessful NOTIFICATION-TYPE
        STATUS               current
        DESCRIPTION  "A rcnUpgradeSuccessful signifies that
                     The switch upgraded successfully."
        ::= { rcTrapsMib 207 }

rcnUpgradeFailure NOTIFICATION-TYPE
        STATUS               current
        DESCRIPTION  "A rcnUpgradeFailure signifies that
                     The switch upgrade failed."
        ::= { rcTrapsMib 208 }

rcnVersionMisMatch NOTIFICATION-TYPE
        STATUS               current
        DESCRIPTION  "A rcnVersionMisMatch signifies that
                     The switch has CPUs on different software versions."
        ::= { rcTrapsMib 209 }

rcnHighCopUtil         NOTIFICATION-TYPE
        OBJECTS       { rc2kCardIndex,
                        rc2kCardPerfCPUUtilization }
        STATUS         current
        DESCRIPTION    "A rcnHighCopUtil signifies that the COP utilization has
                        exceeded for a given slot above the defined thereshold
                        limits"
        ::= { rcTrapsMib 210 }

rcnCfmDualHomeUniClientMepCcmTrap  NOTIFICATION-TYPE
        OBJECTS       { rcCfmMaintenanceEndPointDomainName,
                        rcCfmMaintenanceEndPointAssociationName,
                        rcCfmRemoteMepId,
                        rcCfmLocalMepId,
                        rcCfmRemoteMacAddr,
                        rcCfmIsidId,
                        rcCfmVid,
                        rcCfmMepCcmIndication,
                        rcIsidEndptUserLabel1,
                        rcIsidEndptUserLabel2,
                        rcCfmDirection,
                        rcCfmDhuId}

        STATUS        current
        DESCRIPTION   "A CfmDualHomeUniClientMepCcmtrap signifies that the
                       CCM operational state has been changed
                       for a Dual Home UNI MEP"
        ::= { rcTrapsMib 211 }

rcnCfmFaultAlarm NOTIFICATION-TYPE
        OBJECTS     { rcCfmStatsDefect }
        STATUS      current
        DESCRIPTION
            "A MEP has a persistent defect condition. A notification
            (fault alarm) is sent to the management entity with the OID
            of the MEP that has detected the fault.

            Whenever a MEP has a persistent defect,
            it may or may not generate a Fault Alarm to warn the system
            administrator of the problem, as controlled by the MEP
            Fault Notification Generator State Machine and associated
            Managed Objects. Only the highest-priority defect, as shown
            in Table 20-1, is reported in the Fault Alarm.

            If a defect with a higher priority is raised after a Fault
            Alarm has been issued, another Fault Alarm is issued."
        REFERENCE       "802.1ag clause 12.14.7.7"
        ::= { rcTrapsMib 212 }

rcnPimMaxInterfaceWarnSet NOTIFICATION-TYPE
        STATUS        current
        DESCRIPTION  "A rcnPimMaxInterfaceWarnSet trap signifies that the
                      pim interface count has exceeded the maximum set limit of 200."
        ::= { rcTrapsMib 213 }
                                                                   
rcnPimMaxNeighborsWarnSet NOTIFICATION-TYPE
        STATUS       current 
        DESCRIPTION "A rcnPimMaxNeighborsWarnSet trap signifies that the
                     pim neighbor count has exceeded the maximum set limit of 200."
        ::= { rcTrapsMib 214 } 

rcnPimMaxPassiveInterfaceWarnSet NOTIFICATION-TYPE
        STATUS        current
        DESCRIPTION  "A rcnPimMaxPassiveInterfaceWarnSet trap signifies that the 
                      pim passive interface count has exceeded the maximum set 
                      limit of 2000."
        ::= { rcTrapsMib 215 }

rcnLinkOamRemoteCriticalEventTrap NOTIFICATION-TYPE
        OBJECTS       { rcPortIndex,
			rcLinkOamPeerMacAddress,
			rcLinkOamTrapIndication }
        STATUS        current
        DESCRIPTION   "A rcnLinkOamRemoteCriticalEventTrap is raised when 
		       received a 'critical event' protocol packet from peer, 
		       cleared when the 'critical event' indicator is no longer 
		       set in the received OAMPDU"
        ::= { rcTrapsMib 216}

rcnLinkOamRemoteLoopbackActiveTrap NOTIFICATION-TYPE
        OBJECTS       { rcPortIndex,
			rcLinkOamPeerMacAddress }
        STATUS        current
        DESCRIPTION   "A rcnLinkOamRemoteLoopbackActiveTrap is raised when 
		       remote port has been successfully put into remote 
		       loopback mode"
        ::= { rcTrapsMib 217}

rcnLinkOamRemoteLoopbackFailureTrap NOTIFICATION-TYPE
        OBJECTS       { rcPortIndex,
			rcLinkOamPeerMacAddress }
        STATUS        current
        DESCRIPTION   "A rcnLinkOamRemoteLoopbackFailureTrap is raised when 
		       the remote port cannot be put into remote loopback mode"
        ::= { rcTrapsMib 218}

rcnLinkOamRemoteDiscoveryFailureTrap NOTIFICATION-TYPE
        OBJECTS       { rcPortIndex }
        STATUS        current
        DESCRIPTION   "A rcnLinkOamRemoteDiscoveryFailureTrap is raised 
		       to identify cases where the discovery protocol fails 
		       to execute successfully. Cleared by 
		       rcnLinkOamRemoteDiscoveryTrap"
        ::= { rcTrapsMib 219}

rcnLinkOamRemoteLinkHeartbeatFailureTrap NOTIFICATION-TYPE
        OBJECTS       { rcPortIndex,
			rcLinkOamPeerMacAddress }
        STATUS        current
        DESCRIPTION   "A rcnLinkOamRemoteLinkHeartbeatFailureTrap is raised when 
		       the peer heartbeat message is no longer being received. 
		       Cleared by rcnLinkOamRemoteDiscoveryTrap"
        ::= { rcTrapsMib 221}

rcnCfmEndptClientMltFdTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortMltId,
			rcCfmMonitorCosPriority,
	          	rcCfmThresholdIndication,
			rcCfmActualPercentage,
			rcCfmActualSubPercentage,
			rcCfmAlarmThreshold,
			rcCfmAlarmSubThreshold,
			rcCfmClearThreshold,
			rcCfmClearSubThreshold,
		        rcCfmFdTarget,
		        rcCfmFdAverage,
			rcIsidEndptUserLabel1,
			rcIsidEndptUserLabel2,
		        rcCfmDirection 
		      }
	STATUS	      current
	DESCRIPTION   "A CfmEndptClientMltFdTrap trap signifies that the
		       Frame Delay over Short Period threshold has
		       been crossed.

		       CCM origin:
			   rcCfmMaintenanceEndPointDomainName,  
                     	   rcCfmMaintenanceEndPointAssociationName,
			   rcCfmRemoteMepId,	
			   rcCfmLocalMepId,
		           rcCfmDirection

		       L1-L3 origin:
			   rcCfmRemoteMacAddr,rcCfmIsidId,
			   rcCfmVid, rcPortMltId

		       Customer Label:
			   rcIsidEndptUserLabel1, rcIsidEndptUserLabel2

	 	       FD info:
			  rcCfmThresholdIndication,
			  rcCfmActualPercentage, rcCfmActualSubPercentage,
			  rcCfmAlarmThreshold, rcCfmAlarmSubThreshold,
			  rcCfmClearThreshold, rcCfmClearSubThreshold,
			  rcCfmFdTarget, rcCfmFdAverage"
	::= { rcTrapsMib 222 }

rcnCfmEndptClientMltFdvTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortMltId,
			rcCfmMonitorCosPriority,
	          	rcCfmThresholdIndication,
			rcCfmActualPercentage,
			rcCfmActualSubPercentage,
			rcCfmAlarmThreshold,
			rcCfmAlarmSubThreshold,
			rcCfmClearThreshold,
			rcCfmClearSubThreshold,
		        rcCfmFdvTarget,
		        rcCfmFdvAverage,
			rcIsidEndptUserLabel1,
			rcIsidEndptUserLabel2,
		        rcCfmDirection 
		      }
	STATUS	      current
	DESCRIPTION   "A CfmEndptClientMltFdvTrap trap signifies that the
		       Frame Delay Variation over Short Period threshold has
		       been crossed.

		       CCM origin:
			   rcCfmMaintenanceEndPointDomainName,  
                     	   rcCfmMaintenanceEndPointAssociationName,
			   rcCfmRemoteMepId,	
			   rcCfmLocalMepId,
		           rcCfmDirection

		       L1-L3 origin:
			   rcCfmRemoteMacAddr,rcCfmIsidId,
			   rcCfmVid, rcPortMltId

		       Customer Label:
			   rcIsidEndptUserLabel1, rcIsidEndptUserLabel2

	 	       FDV info:
			  rcCfmThresholdIndication,
			  rcCfmActualPercentage, rcCfmActualSubPercentage,
			  rcCfmAlarmThreshold, rcCfmAlarmSubThreshold,
			  rcCfmClearThreshold, rcCfmClearSubThreshold,
			  rcCfmFdvTarget, rcCfmFdvAverage"
	::= { rcTrapsMib 223 }

rcnCfmEndptClientMltFlrNearEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortMltId,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2,
		        rcCfmDirection
		     }
	STATUS	     current
	DESCRIPTION   "A CfmEndptClientMltFlrNearEndTrap trap signifies that the 
		      Frame Loss Ratio over Short Period threshold has
		      been crossed for ingress data frames."
	::= { rcTrapsMib 224 }

rcnCfmEndptClientMltFlrFarEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortMltId,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2,
		        rcCfmDirection
		     }
	STATUS	     current
	DESCRIPTION   "A CfmEndptClientMltFlrFarEndTrap trap signifies that the 
		      Frame Loss Ratio over Short Period threshold has
		      been crossed for egress data frames."
	::= { rcTrapsMib 225 }

rcnLinkOamRemoteLoopbackTerminateSucceedTrap NOTIFICATION-TYPE
        OBJECTS       { rcPortIndex,
			rcLinkOamPeerMacAddress }
        STATUS        current
        DESCRIPTION   "A rcnLinkOamRemoteLoopbackTerminateSucceedTrap is raised when 
		       the remote loopback mode has been terminated successfully"
        ::= { rcTrapsMib 226}

rcnLinkOamRemoteLoopbackTerminateFailureTrap NOTIFICATION-TYPE
        OBJECTS       { rcPortIndex,
			rcLinkOamPeerMacAddress }
        STATUS        current
        DESCRIPTION   "A rcnLinkOamRemoteLoopbackTerminateFailureTrap is raised when 
		       the remote loopback mode has failed to be terminated"
        ::= { rcTrapsMib 227}

       
rcnUpgradeSuccessfulAckRequired NOTIFICATION-TYPE
        STATUS               current
        DESCRIPTION  "A rcnUpgradeSuccessful signifies that
                     The switch upgraded successfully and acknowlwedgement is required."
        ::= { rcTrapsMib 228 }

rcnLacpNegotiated  NOTIFICATION-TYPE
         OBJECTS         { rcPortIndex }
         STATUS          current
         DESCRIPTION     "A rcnLacpNegotiation signifies if Lacp
                          negotiation successful between link on both ends"
        ::= { rcTrapsMib 231 }

rcnLacpNotNegotiated    NOTIFICATION-TYPE
          OBJECTS         { rcPortIndex }
          STATUS        current
          DESCRIPTION   "A rcnLacpNotNegotiation signifies if LACP not negotiated" 
         ::= { rcTrapsMib 232 }

rcnCtrlPktRateLimitDropTrap NOTIFICATION-TYPE
        OBJECTS       { rcPortIndex,
                        rcPortCtrlPktDropLimit }
        STATUS        current
        DESCRIPTION   "This trap indicates that the number of control packets on the 
                       port has exceeded the configured drop limit."
        ::= { rcTrapsMib 233 }

rcnCtrlPktRateLimitDropClearTrap  NOTIFICATION-TYPE
        OBJECTS       { rcPortIndex,
                        rcPortCtrlPktDropLimit }
        STATUS        current
        DESCRIPTION   "This trap indicates that the count of Control Packets on the 
                       port had exceeded the configured drop limit and is currently 
                       within the configured limits. Clears rcnCtrlPktRateLimitDropTrap."
        ::= { rcTrapsMib 234 }

rcnCtrlPktRateLimitShutdownTrap NOTIFICATION-TYPE
        OBJECTS       { rcPortIndex,
                        rcPortCtrlPktShutdownLimit }
        STATUS        current
        DESCRIPTION   "This trap indicates that the count of Control Packets on the 
                       port has exceeded the configured shutdown limit."
        ::= { rcTrapsMib 235 }

rcnCtrlPktRateLimitShutdownClearTrap NOTIFICATION-TYPE
        OBJECTS       { rcPortIndex,
                        rcPortCtrlPktShutdownLimit }
        STATUS        current
        DESCRIPTION   "This trap indicates that the count of Control Packets on the 
                       port had exceeded the configured shutdown limit and is currently 
                       within the configured limits. Clears rcnCtrlPktRateLimitShutdownTrap."
        ::= { rcTrapsMib 236 }

rcnIngAggregateCirRateLimitDropTrap NOTIFICATION-TYPE
        OBJECTS       { rcTlsRmodLane,
                        rcTlsSlot}
        STATUS               current
        DESCRIPTION  "This trap indicates that the ingress control traffic on the lane has 
                      exceeded the cir limit"
        ::= { rcTrapsMib 237 }

rcnIngAggregateCirRateLimitDropClearTrap  NOTIFICATION-TYPE
        OBJECTS       { rcTlsRmodLane, 
                        rcTlsSlot}
        STATUS               current
        DESCRIPTION  "This trap indicates that the ingress control traffic on the lane had 
                      exceeded the cir limit and it is currently within the 
                      cir limit. Clears rcnIngAggregateCirRateLimitDropTrap."
        ::= { rcTrapsMib 238 }

rcnIngAggregatePirRateLimitDropTrap NOTIFICATION-TYPE
        OBJECTS       { rcTlsRmodLane,
                        rcTlsSlot}
        STATUS               current
        DESCRIPTION  "This trap indicates that the ingress control traffic on the lane has
                      exceeded the pir limit."
        ::= { rcTrapsMib 239 }

rcnIngAggregatePirRateLimitDropClearTrap NOTIFICATION-TYPE
        OBJECTS       { rcTlsRmodLane,
                        rcTlsSlot}
        STATUS               current
        DESCRIPTION  "This trap indicates that the ingress control traffic on the lane had
                      exceeded the pir limit and it is currently within the 
                      limit. Clears rcnIngAggregatePirRateLimitDropTrap."
        ::= { rcTrapsMib 240 }

rcnCfmVlanNodalMepCcmTrap  NOTIFICATION-TYPE
        OBJECTS       { rcCfmMaintenanceEndPointDomainName,
                                   rcCfmMaintenanceEndPointAssociationName,
                                   rcCfmRemoteMepId,
                                   rcCfmLocalMepId,
                                   rcCfmRemoteMacAddr,
                                   rcVlanId,
                                   rcCfmMepCcmIndication,
                                   rcPortUserLabel1,
                                   rcPortUserLabel2,
                                   rcCfmDirection
                                }
        STATUS        current
        DESCRIPTION   "A CfmVlanNodalMepCcm trap signifies that the
                       CCM operations state has been changed for a MEP
                       configured on a vlan. The UserLabels are copied
                       from the UserLabel field of the Vlan. This is a
                       set and clear trap. The clearing is indicated by
                       the rcCfmMepCcmIndication field. "

        ::= { rcTrapsMib 242}

rcnLinkOamRemoteDiscoveryTrap NOTIFICATION-TYPE
        OBJECTS       { rcPortIndex,
			rcLinkOamPeerMacAddress }
        STATUS        current
        DESCRIPTION   "A rcnLinkOamRemoteDiscoveryTrap is raised when 
		       the peer is discovered. Clears rcnLinkOamRemoteDiscoveryFailureTrap
		       and rcnLinkOamRemoteLinkHeartbeatFailureTrap
		       "
        ::= { rcTrapsMib 243}

rcnCfmEndptClientMepIftlvTrap NOTIFICATION-TYPE
        OBJECTS       { rcCfmMaintenanceEndPointDomainName,  
                        rcCfmMaintenanceEndPointAssociationName,
			rcCfmRemoteMepId,	
			rcCfmLocalMepId,
			rcCfmRemoteMacAddr,
		        rcCfmIsidId,
			rcPortIndex,
			rcCfmVid,
			rcCfmIftlvIndication,
			rcIsidEndptUserLabel1,
			rcIsidEndptUserLabel2,
		        rcCfmDirection
			 }
        STATUS        current
        DESCRIPTION   "A rcnCfmEndptClientMepIftlvTrap signifies that there has been
		       a state change in the rcCfmIftlvIndication for the MEP specified
		       "
        ::= { rcTrapsMib 245}

rcnCfmMltEndptClientMepIftlvTrap NOTIFICATION-TYPE
        OBJECTS       { rcCfmMaintenanceEndPointDomainName,  
                        rcCfmMaintenanceEndPointAssociationName,
			rcCfmRemoteMepId,	
			rcCfmLocalMepId,
			rcCfmRemoteMacAddr,
		        rcCfmIsidId,
			rcCfmVid,
			rcPortMltId,
			rcCfmIftlvIndication,
			rcIsidEndptUserLabel1,
			rcIsidEndptUserLabel2,
		        rcCfmDirection
			 }
        STATUS        current
        DESCRIPTION   "A rcnCfmMltEndptClientMepIftlvTrap signifies that there has been
		       a state change in the rcCfmIftlvIndication for the MEP specified
		       "
        ::= { rcTrapsMib 246}

rcnCfmRingEndptClientMepIftlvTrap NOTIFICATION-TYPE
        OBJECTS       { rcCfmMaintenanceEndPointDomainName,  
                        rcCfmMaintenanceEndPointAssociationName,
			rcCfmRemoteMepId,	
			rcCfmLocalMepId,
			rcCfmRemoteMacAddr,
		        rcCfmIsidId,
			rcCfmVid,
			rcIsidEndptRingId,
			rcIsidEndptModId,
			rcIsidEndptEsuPort,
			rcCfmIftlvIndication,
			rcIsidEndptUserLabel1,
			rcIsidEndptUserLabel2,
		        rcCfmDirection
			 }
        STATUS        current
        DESCRIPTION   "A rcnCfmRingEndptClientMepIftlvTrap signifies that there has been
		       a state change in the rcCfmIftlvIndication for the MEP specified
		       "
        ::= { rcTrapsMib 247}

rcnCfmStandEndptClientMepIftlvTrap NOTIFICATION-TYPE
        OBJECTS       { rcCfmMaintenanceEndPointDomainName,  
                        rcCfmMaintenanceEndPointAssociationName,
			rcCfmRemoteMepId,	
			rcCfmLocalMepId,
			rcCfmRemoteMacAddr,
		        rcCfmIsidId,
			rcCfmVid,
			rcPortIndex,
			rcIsidEndptModId,
			rcIsidEndptEsuPort,
			rcCfmIftlvIndication,
			rcIsidEndptUserLabel1,
			rcIsidEndptUserLabel2,
		        rcCfmDirection
			 }
        STATUS        current
        DESCRIPTION   "A rcnCfmStandEndptClientMepIftlvTrap signifies that there has been
		       a state change in the rcCfmIftlvIndication for the MEP specified
		       "
        ::= { rcTrapsMib 248}

rcnCfmDHUniEntptClientMepIftlvTrap  NOTIFICATION-TYPE
        OBJECTS       { rcCfmMaintenanceEndPointDomainName,
                        rcCfmMaintenanceEndPointAssociationName,
                        rcCfmRemoteMepId,
                        rcCfmLocalMepId,
                        rcCfmRemoteMacAddr,
                        rcCfmIsidId,
                        rcCfmVid,
                        rcCfmIftlvIndication,
                        rcIsidEndptUserLabel1,
                        rcIsidEndptUserLabel2,
                        rcCfmDirection,
                        rcCfmDhuId
		      }
        STATUS        current
        DESCRIPTION   "A rcnCfmDHUniEntptClientMepIftlvTrap signifies that there has been
                       a state change in the rcCfmIftlvIndication for a Dual Home UNI MEP"
        ::= { rcTrapsMib 249 }

rcnCfmEndptClientRingFdTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
                        rcIsidEndptRingId,
		 	rcIsidEndptModId,
		 	rcIsidEndptEsuPort,
			rcCfmMonitorCosPriority,
	          	rcCfmThresholdIndication,
			rcCfmActualPercentage,
			rcCfmActualSubPercentage,
			rcCfmAlarmThreshold,
			rcCfmAlarmSubThreshold,
			rcCfmClearThreshold,
			rcCfmClearSubThreshold,
		        rcCfmFdTarget,
		        rcCfmFdAverage,
			rcIsidEndptUserLabel1,
			rcIsidEndptUserLabel2,
		        rcCfmDirection 
		      }
	STATUS	      current
	DESCRIPTION   "A CfmEndptClientRingFdTrap trap signifies that the
		       Frame Delay over Short Period threshold has
		       been crossed.

		       CCM origin:
			   rcCfmMaintenanceEndPointDomainName,  
                     	   rcCfmMaintenanceEndPointAssociationName,
			   rcCfmRemoteMepId,	
			   rcCfmLocalMepId,
		           rcCfmDirection

		       L1-L3 origin:
			   rcCfmRemoteMacAddr,rcCfmIsidId,
			   rcCfmVid,rcIsidEndptRingId,
		           rcIsidEndptModId,rcIsidEndptEsuPort

		       Customer Label:
			   rcIsidEndptUserLabel1, rcIsidEndptUserLabel2

	 	       FD info:
			  rcCfmMonitorCosPriority,rcCfmThresholdIndication,
			  rcCfmActualPercentage, rcCfmActualSubPercentage,
			  rcCfmAlarmThreshold, rcCfmAlarmSubThreshold,
			  rcCfmClearThreshold, rcCfmClearSubThreshold,
			  rcCfmFdTarget, rcCfmFdAverage"
	::= { rcTrapsMib 250 }

rcnCfmEndptClientRingFdvTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
                        rcIsidEndptRingId,
		 	rcIsidEndptModId,
		 	rcIsidEndptEsuPort,
			rcCfmMonitorCosPriority,
	          	rcCfmThresholdIndication,
			rcCfmActualPercentage,
			rcCfmActualSubPercentage,
			rcCfmAlarmThreshold,
			rcCfmAlarmSubThreshold,
			rcCfmClearThreshold,
			rcCfmClearSubThreshold,
		        rcCfmFdvTarget,
		        rcCfmFdvAverage,
			rcIsidEndptUserLabel1,
			rcIsidEndptUserLabel2,
		        rcCfmDirection 
		      }
	STATUS	      current
	DESCRIPTION   "A CfmEndptClientRingFdvTrap trap signifies that the
		       Frame Delay Variation over Short Period threshold has
		       been crossed.

		       CCM origin:
			   rcCfmMaintenanceEndPointDomainName,  
                     	   rcCfmMaintenanceEndPointAssociationName,
			   rcCfmRemoteMepId,	
			   rcCfmLocalMepId,
		           rcCfmDirection

		       L1-L3 origin:
			   rcCfmRemoteMacAddr,rcCfmIsidId,
			   rcCfmVid,rcIsidEndptRingId,
		 	   rcIsidEndptModId,rcIsidEndptEsuPort

		       Customer Label:
			   rcIsidEndptUserLabel1, rcIsidEndptUserLabel2

	 	       FDV info:
			  rcCfmMonitorCosPriority,rcCfmThresholdIndication,
			  rcCfmActualPercentage, rcCfmActualSubPercentage,
			  rcCfmAlarmThreshold, rcCfmAlarmSubThreshold,
			  rcCfmClearThreshold, rcCfmClearSubThreshold,
			  rcCfmFdvTarget, rcCfmFdvAverage"
	::= { rcTrapsMib 251 }

rcnCfmEndptClientRingFlrNearEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
                        rcIsidEndptRingId,
		 	rcIsidEndptModId,
		 	rcIsidEndptEsuPort,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2,
		        rcCfmDirection
		     }
	STATUS	     current
	DESCRIPTION   "A CfmEndptClientRingFlrNearEndTrap trap signifies that the 
		      Frame Loss Ratio over Short Period threshold has
		      been crossed for ingress data frames."
	::= { rcTrapsMib 252 }

rcnCfmEndptClientRingFlrFarEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
                        rcIsidEndptRingId,
		 	rcIsidEndptModId,
		 	rcIsidEndptEsuPort,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2,
		        rcCfmDirection
		     }
	STATUS	     current
	DESCRIPTION   "A CfmEndptClientRingFlrFarEndTrap trap signifies that the 
		      Frame Loss Ratio over Short Period threshold has
		      been crossed for egress data frames."
	::= { rcTrapsMib 253 }

rcnCfmEndptClientStandAloneFdTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortIndex,
			rcIsidEndptModId,
			rcIsidEndptEsuPort,
			rcCfmMonitorCosPriority,
	          	rcCfmThresholdIndication,
			rcCfmActualPercentage,
			rcCfmActualSubPercentage,
			rcCfmAlarmThreshold,
			rcCfmAlarmSubThreshold,
			rcCfmClearThreshold,
			rcCfmClearSubThreshold,
		        rcCfmFdTarget,
		        rcCfmFdAverage,
			rcIsidEndptUserLabel1,
			rcIsidEndptUserLabel2,
		        rcCfmDirection 
		      }
	STATUS	      current
	DESCRIPTION   "A CfmEndptClientStandAloneFdTrap trap signifies that the
		       Frame Delay over Short Period threshold has
		       been crossed.

		       CCM origin:
			   rcCfmMaintenanceEndPointDomainName,  
                     	   rcCfmMaintenanceEndPointAssociationName,
			   rcCfmRemoteMepId,	
			   rcCfmLocalMepId,
		           rcCfmDirection

		       L1-L3 origin:
			   rcCfmRemoteMacAddr,rcCfmIsidId,
			   rcCfmVid,rcPortIndex,
		           rcIsidEndptModId,rcIsidEndptEsuPort

		       Customer Label:
			   rcIsidEndptUserLabel1, rcIsidEndptUserLabel2

	 	       FD info:
			  rcCfmMonitorCosPriority,rcCfmThresholdIndication,
			  rcCfmActualPercentage, rcCfmActualSubPercentage,
			  rcCfmAlarmThreshold, rcCfmAlarmSubThreshold,
			  rcCfmClearThreshold, rcCfmClearSubThreshold,
			  rcCfmFdTarget, rcCfmFdAverage"
	::= { rcTrapsMib 254 }

rcnCfmEndptClientStandAloneFdvTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortIndex,
		 	rcIsidEndptModId,
		 	rcIsidEndptEsuPort,
			rcCfmMonitorCosPriority,
	          	rcCfmThresholdIndication,
			rcCfmActualPercentage,
			rcCfmActualSubPercentage,
			rcCfmAlarmThreshold,
			rcCfmAlarmSubThreshold,
			rcCfmClearThreshold,
			rcCfmClearSubThreshold,
		        rcCfmFdvTarget,
		        rcCfmFdvAverage,
			rcIsidEndptUserLabel1,
			rcIsidEndptUserLabel2,
		        rcCfmDirection 
		      }
	STATUS	      current
	DESCRIPTION   "A CfmEndptClientStandAloneFdvTrap trap signifies that the
		       Frame Delay Variation over Short Period threshold has
		       been crossed.

		       CCM origin:
			   rcCfmMaintenanceEndPointDomainName,  
                     	   rcCfmMaintenanceEndPointAssociationName,
			   rcCfmRemoteMepId,	
			   rcCfmLocalMepId,
		           rcCfmDirection

		       L1-L3 origin:
			   rcCfmRemoteMacAddr,rcCfmIsidId,
			   rcCfmVid,rcPortIndex,
		 	   rcIsidEndptModId,rcIsidEndptEsuPort

		       Customer Label:
			   rcIsidEndptUserLabel1, rcIsidEndptUserLabel2

	 	       FDV info:
			  rcCfmMonitorCosPriority,rcCfmThresholdIndication,
			  rcCfmActualPercentage, rcCfmActualSubPercentage,
			  rcCfmAlarmThreshold, rcCfmAlarmSubThreshold,
			  rcCfmClearThreshold, rcCfmClearSubThreshold,
			  rcCfmFdvTarget, rcCfmFdvAverage"
	::= { rcTrapsMib 255 }

rcnCfmEndptClientStandAloneFlrNearEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortIndex,
		 	rcIsidEndptModId,
		 	rcIsidEndptEsuPort,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2,
		        rcCfmDirection
		     }
	STATUS	     current
	DESCRIPTION   "A CfmEndptClientStandAloneFlrNearEndTrap trap signifies that the 
		      Frame Loss Ratio over Short Period threshold has
		      been crossed for ingress data frames."
	::= { rcTrapsMib 256 }

rcnCfmEndptClientStandAloneFlrFarEndTrap NOTIFICATION-TYPE
	OBJECTS	      { rcCfmMaintenanceEndPointDomainName,  
                        rcCfmMaintenanceEndPointAssociationName,
			rcCfmRemoteMepId,	
			rcCfmLocalMepId,
			rcCfmRemoteMacAddr,
		        rcCfmIsidId,
		        rcCfmVid,
			rcPortIndex,
		 	rcIsidEndptModId,
		 	rcIsidEndptEsuPort,
	             	rcCfmMonitorCosPriority,
			rcCfmThresholdIndication,
			rcCfmActualPercentage,
			rcCfmActualSubPercentage,
			rcCfmAlarmThreshold,
			rcCfmAlarmSubThreshold,
			rcCfmClearThreshold,
			rcCfmClearSubThreshold,
			rcIsidEndptUserLabel1,
			rcIsidEndptUserLabel2,
		        rcCfmDirection
		     }
	STATUS	     current
	DESCRIPTION   "A CfmEndptClientStandAloneFlrFarEndTrap trap signifies that the 
		      Frame Loss Ratio over Short Period threshold has
		      been crossed for egress data frames."
	::= { rcTrapsMib 257 }

rcnAutoSaveFailed NOTIFICATION-TYPE
        STATUS               current
        DESCRIPTION  "A rcnAutoSaveFailed signifies that Autosave of the configurations on the switch failed because of the lack of storage space."
        ::= { rcTrapsMib 258 }

rcnEgrAggregateCirRateLimitDropTrap NOTIFICATION-TYPE
        OBJECTS       { rcTlsRmodLane,
                        rcTlsSlot}
        STATUS               current
        DESCRIPTION  "This trap indicates that the egress control traffic on the lane has
                      exceeded the cir limit."
        ::= { rcTrapsMib 259 }

rcnEgrAggregateCirRateLimitDropClearTrap  NOTIFICATION-TYPE
        OBJECTS       { rcTlsRmodLane,
                        rcTlsSlot}
        STATUS               current
        DESCRIPTION  "This trap indicates that the egress control traffic on the lane had
                      exceeded the cir limit and it is currently within the
                      limit. Clears rcnEgrAggregateCirRateLimitDropTrap."
        ::= { rcTrapsMib 260 }

rcnEgrAggregatePirRateLimitDropTrap NOTIFICATION-TYPE
        OBJECTS       { rcTlsRmodLane,
                        rcTlsSlot}
        STATUS               current
        DESCRIPTION  "This trap indicates that the egress control traffic on the lane has
                      exceeded the pir limit."
        ::= { rcTrapsMib 261 }

rcnEgrAggregatePirRateLimitDropClearTrap NOTIFICATION-TYPE
        OBJECTS       { rcTlsRmodLane,
                        rcTlsSlot}
        STATUS               current
        DESCRIPTION  "This trap indicates that the egress control traffic on the lane had
                      exceeded the pir limit and it is currently within the
                      limit. Clears rcnEgrAggregatePirRateLimitDropTrap."
        ::= { rcTrapsMib 262 }


rcnLinkOamRemoteDyingGaspTrap NOTIFICATION-TYPE
        OBJECTS       { rcPortIndex,
			rcLinkOamPeerMacAddress,
			rcLinkOamTrapIndication }
        STATUS        current
        DESCRIPTION   "A rcnLinkOamRemoteDyingGaspTrap is raised when received a 
		       'dying gasp' protocol packet from peer (for example, the 
			far-end line card has a power loss), cleared when 'dying 
			gasp' indicator is no longer set in the received OAMPDU"
        ::= { rcTrapsMib 263}

rcnLinkOamRemoteLinkFaultTrap NOTIFICATION-TYPE
        OBJECTS       { rcPortIndex,
			rcLinkOamPeerMacAddress,
			rcLinkOamTrapIndication }
        STATUS        current
        DESCRIPTION   "A rcnLinkOamRemoteLinkFaultTrap is raised raised when 
		       received a 'link fault' protocol packet from peer, 
		       cleared when the 'link fault' indicator is no longer 
		       set in the received OAMPDU"
        ::= { rcTrapsMib 264} 

rcnLegacyCardDetected NOTIFICATION-TYPE
        OBJECTS       { rc2kCardIndex }
        STATUS        current
        DESCRIPTION  "A rcnLegacyCardDetected trap signifies that a legacy card has
                      been detected on the cahssis, rc2kCardIndex indicates the slot
                      number of legacy card."
        ::= { rcTrapsMib 265 }
                                  
rcnPrFilterRspMemoryFull  NOTIFICATION-TYPE
        OBJECTS       { rcPrFilterAclId, 
			rc2kCardIndex }
        STATUS        current
        DESCRIPTION  "A rcnPrFilterRspMemoryFull trap signifies that RSP memory is
		      full for Power Ranger filter configuration. rcPrFilterAclId
		      indicates the ACL, on which ACL RSP memory full occurs. 
		      rc2kCardIndex indicates the slot number, on which RSP memory 
		      full event occurs."
        ::= { rcTrapsMib 266 }

rcnPrFilterStatsCntExst  NOTIFICATION-TYPE
        OBJECTS       { rcPrFilterAclId, 
			rc2kCardIndex }
        STATUS        current
        DESCRIPTION  "A rcnPrFilterStatsCntExst trap signifies that RSP filter stats 
		      counters have been run out. When this happens, affected filters 
		      won't get their counter updated by filter forwarding engine. 
		      rcPrFilterAclId indicates the ACL, on which filter stats counter
		      exhaust occurs. rc2kCardIndex indicates the slot number, on which 
		      filter stats counter exhaust occurs."
        ::= { rcTrapsMib 267 }

rcnAuthenticationSuccess NOTIFICATION-TYPE
        OBJECTS       { rcLoginUserName, rcLoginHostIpAddress }
        STATUS        current
        DESCRIPTION  "A rcnAuthenticationSuccess trap signifies that a login
                      is success. Trap includes login username and host ip"
        ::= { rcTrapsMib 268 }

rcnCardInsert NOTIFICATION-TYPE
        OBJECTS       { rc2kCardIndex, rcSlotType }
        STATUS        current
        DESCRIPTION  "A rcnCardInsert trap signifies that a card/module
                      is inserted into the chassis"
        ::= { rcTrapsMib 269 }

rcnCardRemove NOTIFICATION-TYPE
        OBJECTS       { rc2kCardIndex, rcSlotType }
        STATUS        current
        DESCRIPTION  "A rcnCardRemove trap signifies that a card/module
                      is removed from the chassis"
        ::= { rcTrapsMib 270 }

rcnChasFanFail NOTIFICATION-TYPE
        OBJECTS       { rcFanZoneType, rcFanTrayId, rcFanUnitId }
        STATUS        current
        DESCRIPTION  "A rcnChasFanFail trap indicates that a fan unit
                      of a fan tray in a fan zone has fault."
        ::= { rcTrapsMib 271 }

rcnChasFanOk NOTIFICATION-TYPE
        OBJECTS       { rcFanZoneType, rcFanTrayId, rcFanUnitId }
        STATUS        current
        DESCRIPTION  "A rcnChasFanOk trap indicates that a fan unit
                      of a fan tray in a fan zone has recovered from
                      previously detected fan fault."
        ::= { rcTrapsMib 272 }

rcnCardOverheat NOTIFICATION-TYPE
        OBJECTS       { rc2kCardIndex, rcSlotType, rcCardTemp }
        STATUS        current
        DESCRIPTION  "A rcnCardOverheat trap indicates that a card temperature
                      has exceeded the alarm threshold temperature.
                      Starting from VSP9K 4.0 release, a new rcn2kCardOverheat
                      trap has been created that should be used instead of this trap."
        ::= { rcTrapsMib 273 }

rcnCardNormalTemp NOTIFICATION-TYPE
        OBJECTS       { rc2kCardIndex, rcSlotType, rcCardTemp }
        STATUS        current
        DESCRIPTION  "A rcnCardNormalTemp trap indicates that a card
                      temperature has been cool down from previously detected
                      overheat condition.
                      Starting from VSP9K 4.0 release, a new rcn2kCardNormalTemp
                      trap has been created that should be used instead of this trap."
        ::= { rcTrapsMib 274 }

rcnCardOverheatShutDown NOTIFICATION-TYPE
        OBJECTS       { rc2kCardIndex, rcSlotType, rcCardTemp }
        STATUS        current
        DESCRIPTION  "A rcnCardOverheatShutDown trap indicates that a card
                      has been shut down due to persistent temperature overheat
                      for 15 minutes or temperature has exceeded the shut down
                      threshold temperature.
                      Starting from VSP9K 4.0 release, a new rcn2kCardOverheatShutDown
                      trap has been created that should be used instead of this trap."
        ::= { rcTrapsMib 275 }

rcnCardCpuUtilizationHigh NOTIFICATION-TYPE
        OBJECTS       { rc2kCardIndex, rcSlotType, rcCpuUtilization }
        STATUS        current
        DESCRIPTION  "A rcnCardCpuUtilizationHigh trap indicates that 5-minute
                      CPU utilization average on this slot is above 90%."
        ::= { rcTrapsMib 276 }

rcnCardCpuUtilizationNormal NOTIFICATION-TYPE
        OBJECTS       { rc2kCardIndex, rcSlotType, rcCpuUtilization }
        STATUS        current
        DESCRIPTION  "A rcnCardCpuUtilizationNormal trap indicates that 5-minute
                      CPU utilization average on this slot is below 75%."
        ::= { rcTrapsMib 277 }

rcnIsisPlsbBvidMismatchTrap  NOTIFICATION-TYPE
        OBJECTS       { rcIsisLocalSysId,
			rcIsisLocalPrimaryBvid,
			rcIsisLocalPrimaryTieBrkAlg,
			rcIsisLocalSecondaryBvid,
			rcIsisLocalSecondaryTieBrkAlg,
			rcIsisNgbSysId,
			rcIsisNgbPrimaryBvid,
			rcIsisNgbPrimaryTieBrkAlg,
			rcIsisNgbSecondaryBvid, 
			rcIsisNgbSecondaryTieBrkAlg,   
                        rcIsisLocalBvidCounter,
                        rcIsisNgbBvidCounter,
                        rcIsisPlsbTrapType,
                        rcIsisTrapIndicator,
                        rcIsisNgbHostName
                        }
        STATUS        current
        DESCRIPTION   "A PLSB ISIS trap signifies that a Hello packet with mismatched 
                       B-VIDs is received"
        ::= { rcTrapsMib 278 }

rcnIsisPlsbSmltVirtBmacMismatchTrap  NOTIFICATION-TYPE
        OBJECTS       { rcIsisLocalVirtualBmac,
			rcIsisPeerVirtualBmac,
                        rcIsisPlsbTrapType,
                        rcIsisTrapIndicator}
        STATUS        current
        DESCRIPTION   "A PLSB ISIS trap signifies that Virtual BMAC configured in the switch
                       is different from virtual BMAC configured in the IST peer"
        ::= { rcTrapsMib 279 }

rcnIsisPlsbSmltPeerBmacMismatchTrap  NOTIFICATION-TYPE
        OBJECTS       { rcIsisSysId,
			rcIsisSmltPeerSysId,
                        rcIsisPlsbTrapType,
                        rcIsisTrapIndicator}
        STATUS        current
        DESCRIPTION   "A PLSB ISIS trap signifies that either the Smlt Peer BMAC configured 
                       in the IST peer is different from the ISIS SystemId of the local switch OR
                       The Smlt peer BMAC configured in the local switch is different from
                       the ISIS systemId of the IST peer"

        ::= { rcTrapsMib 280 }

rcnIsisPlsbAdjStateTrap  NOTIFICATION-TYPE
        OBJECTS       { rcIsisNgbSysId,
                        rcIsisLocalInterface,                
                        rcIsisPlsbTrapType,
                        rcIsisAdjState,
                        rcIsisNgbHostName}
        STATUS        current
        DESCRIPTION   "A PLSB ISIS trap signifies ISIS adjacency state change."
        ::= { rcTrapsMib 281 }         

rcnIsisPlsbDuplicateNnameTrap  NOTIFICATION-TYPE
        OBJECTS       { rcIsisNgbNickname, 
                        rcIsisPlsbTrapType,
                        rcIsisTrapIndicator,
                        rcIsisNgbSysId,
                        rcIsisDuplicateNnameCounter, 
                        rcIsisNgbHostName}
        STATUS        current
        DESCRIPTION   "A PLSB ISIS trap signifies that a LSP with duplicate
                       nickname is received, this trap should be generated 
                       by all the switches in the network."
        ::= { rcTrapsMib 282 }

rcnIsisPlsbSmltSplitBebMismatchTrap NOTIFICATION-TYPE
        OBJECTS       { rcIsisLocalSmltSplitBeb,
                        rcIsisPeerSmltSplitBeb,
                        rcIsisPlsbTrapType,
                        rcIsisTrapIndicator}
        STATUS        current
        DESCRIPTION   "A PLSB ISIS trap signifies that the Smlt Split-Beb configured in the local
                       switch and IST peer are same. One IST switch shoule be configured as 
                       Split-Beb primary and the IST peer should be configured as Split-Beb
                       secondary."

        ::= { rcTrapsMib 283 }

rcnIsisPlsbMultiLinkAdjTrap NOTIFICATION-TYPE
        OBJECTS       { rcIsisNgbSysId,
                        rcIsisLocalInterface,
                        rcIsisPrevInterface,
                        rcIsisPlsbTrapType,
                        rcIsisNgbHostName,
                        rcIsisTrapIndicator}
        STATUS        current
        DESCRIPTION   "A PLSB ISIS trap signifies that multiple ISIS adjacencies are formed with 
                       the same ISIS node."

        ::= { rcTrapsMib 284 }

rcnaSshSessionLogout NOTIFICATION-TYPE
        OBJECTS       { rcLoginHostAddressType, rcLoginHostInetAddress }
        STATUS        current
        DESCRIPTION   "A rcnaSshSessionLogout trap signifies that there
                       is a SSH session logout. This trap deprecates the
                       rcnSshSessionLogout trap."
        ::= { rcTrapsMib 285 }

rcnaSshUnauthorizedAccess NOTIFICATION-TYPE
        OBJECTS       { rcLoginHostAddressType, rcLoginHostInetAddress }
        STATUS        current
        DESCRIPTION   "A rcnaSshUnauthorizedAccess trap signifies that
                       an unauthorized access has occured. This trap
                       deprecates the rcnSshUnauthorizedAccess trap."
        ::= { rcTrapsMib 286 }

rcnaAuthenticationSuccess NOTIFICATION-TYPE
        OBJECTS       { rcLoginUserName, rcLoginHostAddressType, rcLoginHostInetAddress }
        STATUS        current
        DESCRIPTION  "A rcnaAuthenticationSuccess trap signifies that a login
                      is success. Trap includes login username and address
                      type and inet address. This trap deprecates the
                      rcnAuthenticationSuccess trap."
        ::= { rcTrapsMib 287 }

rcnaSshSessionLogin NOTIFICATION-TYPE
        OBJECTS       { rcLoginHostAddressType, rcLoginHostInetAddress }
        STATUS        current
        DESCRIPTION   "A rcnaSshSessionLogin trap signifies that there
                       is a SSH session login. This trap deprecates the
                       rcnSshSessionLogin trap."
        ::= { rcTrapsMib 288 }

rcnVLacpFlapDetectShutDown NOTIFICATION-TYPE
        OBJECTS       { rcPortIndex }
        STATUS        current
        DESCRIPTION   "A rcVLacpFlapDetectShutDown trap signifies that the
                       port is shut down because rcPortVLacpFlapFrequency
                       number of VLACP flaps were detected within
                       rcPortVLacpFlapInterval seconds on this port. 
                       The port can be brought UP by toggling
                       the port admin state manually."
        ::= { rcTrapsMib 289 }

rcnWlanTrap     NOTIFICATION-TYPE
        OBJECTS {rcWlanNotificationErrorType,
                 rcWlanNotificationTrapInfo,
                 rcWlanNotificationMobilityTunnelPeerId,
                 rcWlanNotificationMobTunnelAddressType,
                 rcWlanNotificationMobTunnelAddress,
                 rcWlanNotificationMobTunnelMVlanName }
        STATUS  current
        DESCRIPTION     "A trap for WLAN to report errors"
        ::= { rcTrapsMib 290}

rcnAuthenticationFailureLoginAttemptsTrap	NOTIFICATION-TYPE
	OBJECTS		{ rcCliPasswordAccountUserName,
			  rcCliPasswordUserAccessLevel }
	STATUS		current
	DESCRIPTION	"An rcnAuthenticationFailureLoginAttemptsTrap signifies
	    		an unsuccessful login attempt by a user beyond the 
			maximum number of allowed login attempts."
        ::= { rcTrapsMib 291 }


rcnUserAccountIdleTimeExpireTrap	NOTIFICATION-TYPE
	OBJECTS		{ rcCliPasswordAccountUserName,
			  rcCliPasswordUserAccessLevel }
	STATUS		current
	DESCRIPTION	"An rcnUserAccountIdleTimeExpireTrap signifies that
	    		a user did not login within the idle time configured
			and the account will not be disable."
        ::= { rcTrapsMib 292 }

rcnBfdNewStatusChange NOTIFICATION-TYPE
        OBJECTS      { rcBfdTmpSessDiscriminator,
                       rcBfdTmpSessRemoteDiscr,
                       rcBfdTmpSessAddr,
                       rcBfdTmpSessState,
                       rcBfdTmpSessDestAddr,
                       rcBfdTmpSessOldState  }
        STATUS       current
        DESCRIPTION  "A rcnBfdNewStatusChange signifies that the status
	              of BFD session changed."
        ::= { rcTrapsMib 293 }

rcnLacpMisconfigTrap NOTIFICATION-TYPE
        OBJECTS      { rcPortIndex, 
		       rcLacpMisconfigType }
        STATUS       current
        DESCRIPTION   "A link aggregation misconfiguration trap signifies that,
	              this port is receiving LACP PDU without LACP being configured completely."
        ::= { rcTrapsMib 294}

rcnSlotPowerAvailableTrap NOTIFICATION-TYPE
        OBJECTS      { rc2kCardIndex, 
		       rcSlotType,
		       rcSlotPowerStatus }
        STATUS       current
        DESCRIPTION   "A rcnSlotPowerAvailableTrap signifies whether
	              there is enough power to boot up the card in slot."
        ::= { rcTrapsMib 295 }

rcnaBfdStatusChange NOTIFICATION-TYPE
        OBJECTS      { rcBfdTmpSessDiscriminator,
                       rcBfdTmpSessRemoteDiscr,
                       rcBfdTmpSessAddrType,
                       rcBfdTmpSessAddr,
                       rcBfdTmpSessState,
                       rcBfdTmpSessDestAddr,
                       rcBfdTmpSessOldState  }
        STATUS       current
        DESCRIPTION  "A rcnaBfdStatusChange signifies that the status
                      of BFD session changed. rcBfdTmpSessAddrType
                      indicates the address type for rcBfdTmpSessAddr
                      and rcBfdTmpSessDestAddr.
                      This trap deprecates rcnBfdNewStatusChange"
        ::= { rcTrapsMib 296 }
        
rcnaBfdSessExceedThreshold NOTIFICATION-TYPE
        OBJECTS      { rcBfdTmpSessDiscriminator, 
                       rcBfdTmpSessAddrType, 
                       rcBfdTmpSessAddr }
        STATUS	     current
        DESCRIPTION  "A rcnaBfdSessExceedThreshold signifies that 
                      the BFD session has exceeded system limit and hence
                      creation of new session failed.
                      This trap deprecates rcnBfdSessExceedThreshold"
        ::= { rcTrapsMib 297 }

rcn2kCardShutDownTrap NOTIFICATION-TYPE
        OBJECTS       { rc2kCardIndex, 
                        rcSlotType, 
                        rc2kCardShutDownReason }
        STATUS        current
        DESCRIPTION   "A rcn2kCardShutDown trap signifies card shutting down 
		      reason."
        ::= { rcTrapsMib 298 }

rcnMaxMacEntriesTrap NOTIFICATION-TYPE
        STATUS        current
        DESCRIPTION   "A rcMaxMacEntries trap signifies that the
                      SNMPv2 entity, acting in an agent role, has
                      detected that the maximum number of supported Mac
                      Entries(64000) has been reached."
        ::= { rcTrapsMib 299 }

rcn2kCardOverheat NOTIFICATION-TYPE
        OBJECTS       { rc2kCardIndex, 
                        rcSlotType }
        STATUS        current
        DESCRIPTION  "A rcn2kCardOverheat trap indicates that the card temperature
                      has exceeded the alarm threshold temperature. This trap will
                      be followed by the rcn2kCardZoneOverheat trap that specifies
                      which zone's temperature has crossed the alarm threshold.
                      This trap is created in VSP9K 4.0 release and is intended
                      to replace the existing rcnCardOverheat."
        ::= { rcTrapsMib 300 }

rcn2kCardZoneOverheat NOTIFICATION-TYPE
        OBJECTS       { rc2kCardIndex, 
                        rcSlotType, 
                        rc2kCardZoneTemperature, 
                        rc2kCardTemperatureZoneInfo }
        STATUS        current
        DESCRIPTION  "A rcn2kCardZoneOverheat trap indicates which zone on the card
                      has exceeded the alarm threshold temperature."
        ::= { rcTrapsMib 301 }

rcn2kCardZoneNormalTemp NOTIFICATION-TYPE
        OBJECTS       { rc2kCardIndex, 
                        rcSlotType, 
                        rc2kCardZoneTemperature, 
                        rc2kCardTemperatureZoneInfo }
        STATUS        current
        DESCRIPTION  "A rcn2kCardZoneNormalTemp trap indicates that a zone
                      temperature on the card has cooled down from a previously 
                      detected overheat condition."
        ::= { rcTrapsMib 302 }

rcn2kCardNormalTemp NOTIFICATION-TYPE
        OBJECTS       { rc2kCardIndex, 
                        rcSlotType }
        STATUS        current
        DESCRIPTION  "A rcn2kCardNormalTemp trap indicates that the card
                      temperature has cooled down from a previously detected
                      overheat condition. This trap is generated only after the 
                      temperature on all the zones on the card have dropped below
                      the alarm thresholds.
                      This trap is created in VSP9K 4.0 release and is intended
                      to replace the existing rcnCardNormalTemp."
        ::= { rcTrapsMib 303 }

rcn2kCardOverheatShutDown NOTIFICATION-TYPE
        OBJECTS       { rc2kCardIndex, 
                        rcSlotType, 
                        rc2kCardZoneTemperature, 
                        rc2kCardTemperatureZoneInfo }
        STATUS        current
        DESCRIPTION  "A rcn2kCardOverheatShutDown trap indicates that a card
                      has been shut down because the temperature has exceeded 
                      the shut down threshold temperature.
                      This trap is created in VSP9K 4.0 release and is intended
                      to replace the existing rcnCardOverheatShutDown."
        ::= { rcTrapsMib 304 }

rcnIsisSpbmSmltVirtBmacMisconfigTrap NOTIFICATION-TYPE
        OBJECTS       { rcIsisSmltVirtBmacMisconfigNodeSysId,
                        rcIsisPlsbTrapType,
                        rcIsisSmltVirtBmacMisconfigNodeHostName,
                        rcIsisTrapIndicator}
        STATUS        current
        DESCRIPTION   "A SPBM ISIS trap signifies that SMLT virtual BMAC 
                       has been used by nodes other than the SMLT boxes 
                       as system-id or MAC."
        ::= { rcTrapsMib 305 } 

rcnPortChannelizedStateChangeTrap NOTIFICATION-TYPE
	OBJECTS { rcPortIndex,rcChannelizedPortAdminMode}
        STATUS  current
        DESCRIPTION
                "A rcnPortChannelizedStateChangeTrap trap signifies that a port 
		channelized state has changed by enabling/disabling from admin."
        ::= { rcTrapsMib 306 }
    
rcnDNSv6RequestResponse NOTIFICATION-TYPE
        OBJECTS       {rcSysDnsServerIpv6Addr, rcSysDnsRequestType }
        STATUS        current
        DESCRIPTION   "A rcDNSv6RequestResponseTrap trap signifies that the
                       switch had sent a query to the DNS server or it had
                       received a successful response from the DNS Server"
        ::= { rcTrapsMib 307 }

rcnMldNewGroupMemberTrap NOTIFICATION-TYPE
        OBJECTS       { rcMldNewGroupIfIndex,
                        rcMldNotificationNewGroupIpv6Address,
                        rcMldNotificationNewGroupInPort,
                        rcMldNotificationNewGroupMembers }
        STATUS        current
        DESCRIPTION   "An MldNewGroupMember  trap signifies that a
                       new member has come on an interface."
        ::= { rcTrapsMib 308 }

rcnMldLossGroupMemberTrap NOTIFICATION-TYPE
        OBJECTS       { rcMldNotificationNewGroupMembers,
                        rcMldNotificationNewGroupIpv6Address,
                        rcMldNotificationNewGroupInPort,
                        rcMldNewGroupIfIndex }
        STATUS        current
        DESCRIPTION   "An MldLossGroupMember  trap signifies that a
                       group member has been lost on an interface."
        ::= { rcTrapsMib 309 }

rcnMldNewQuerierTrap NOTIFICATION-TYPE
        OBJECTS       { rcMldNotificationInterfaceIfIndex,
                        mldInterfaceQuerier }
        STATUS        current
        DESCRIPTION   "An mldNewQuerier trap signifies that a new
                       querier has come up on an interface."
        ::= { rcTrapsMib 310 }

rcnMldQuerierChangeTrap NOTIFICATION-TYPE
        OBJECTS       { rcMldNotificationInterfaceIfIndex,
                        rcMldInterfaceExtnNewQuerier,
                        mldInterfaceQuerier }
        STATUS        current
        DESCRIPTION   "An rcMldQuerierChange trap signifies that
                       the querier has changed."
        ::= { rcTrapsMib 311 }

rcnIsisPlsbGlobalDuplicateSysidTrap NOTIFICATION-TYPE
        OBJECTS       { rcIsisLocalSysId,
                        rcIsisLocalHostName,
			rcIsisLocalChassisMac,
			rcIsisRemoteHostName,
			rcIsisRemoteChassisMac,
			rcIsisPlsbTrapType,
			rcIsisTrapIndicator }
        STATUS        current
        DESCRIPTION   "A PLSB ISIS trap signifies that a remote node is 
	    	       detected with same system-id as the local node.
		       ISIS disabled globally."
        ::= { rcTrapsMib 312 }

rcnMRouteIpv6IngressThresholdExceeded NOTIFICATION-TYPE
        OBJECTS      { rcMRouteIpv6IngressRecInUse,
                       rcMRouteIpv6IngressThreshold }
        STATUS        current
        DESCRIPTION  "This notification is generated when the number of
                      mroute6 ingress records exceeds the ingress threshold."
        ::= { rcTrapsMib 313 }

rcnMRouteIpv6EgressThresholdExceeded NOTIFICATION-TYPE
        OBJECTS      { rcMRouteIpv6EgressRecInUse,
                       rcMRouteIpv6EgressThreshold }
        STATUS        current
        DESCRIPTION  "This notification is generated when the number of
                      mroute6 egress records exceeds the egress threshold."
        ::= { rcTrapsMib 314 }

rcnIsisPlsbLocalDuplicateNnameTrap  NOTIFICATION-TYPE
        OBJECTS       { rcIsisLocalNickname,
                        rcIsisLocalSysId,
                        rcIsisPreviousSysId,
                        rcIsisLocalHostName,
                        rcIsisPlsbTrapType,
                        rcIsisTrapIndicator}
        STATUS        current
        DESCRIPTION   "A PLSB ISIS trap signifies that our old incarnation 
	    	       of the LSP with different Sys-Id with the same nickname 
		       has not timed out yet. ISIS disabled globally." 
        ::= { rcTrapsMib 315 }

rcnIsisPlsbGlobalDuplicateNnameTrap  NOTIFICATION-TYPE
        OBJECTS       { rcIsisLocalNickname,
                        rcIsisLocalHostName,
                        rcIsisLocalChassisMac,                
                        rcIsisRemoteHostName,                
                        rcIsisRemoteChassisMac,                
                        rcIsisPlsbTrapType,
                        rcIsisTrapIndicator}
        STATUS        current
        DESCRIPTION   "A PLSB ISIS trap signifies that a remote node is 
	    	       detected with same nickname as the local node.
		       ISIS disabled globally." 
        ::= { rcTrapsMib 316 }

rcnPlugModInsertedInNotRecommendedPortTrap  NOTIFICATION-TYPE
        OBJECTS      {  rcPortIndex,
	                rcPluggableModuleDescription
		     }
        STATUS       current
        DESCRIPTION  "A rcnPlugModInsertedInNotRecommendedPortTrap signifies that the LR4 QSFP+
	              is inserted in to a not recommended port. It set alaem which will be cleared
		      by rcnPlugModRemovedFromRecommendedPortTrap"
        ::= { rcTrapsMib 317 }
	
rcnPlugModRemovedFromNotRecommendedPortTrap  NOTIFICATION-TYPE
        OBJECTS      {  rcPortIndex }
        STATUS       current
        DESCRIPTION  "A rcnPlugModRemovedFromNotRecommendedPortTrap signifies that the LR4 QSFP+
	              is removed from a not recommened port. It clears the alarm which is set
		      by rcnPlugModInsertedInNotRecommendedPortTrap"
        ::= { rcTrapsMib 318 }
    
rcnBpduGuardPortShutdown NOTIFICATION-TYPE
    OBJECTS       { rcPortIndex, rcPortBpduGuardTimeout }
    STATUS        current
    DESCRIPTION   "This notification will be generated when a port,
    		  which has BPDU guard enabled, is shutdown. It is cleared
		  by rcnBpduGuardPortShutdownTimerExpired"
    ::= { rcTrapsMib 319 }

rcnBpduGuardPortShutdownTimerExpired NOTIFICATION-TYPE
    OBJECTS       { rcPortIndex}
    STATUS        current
    DESCRIPTION   "This notification will be generated when a port,
    		  which has BPDU guard enabled and is under shutdown timer,
		  and the timer expires. It clears the alarm rcnBpduGuardPortShutdown"
    ::= { rcTrapsMib 320 }

rcnIpv6FhsSnoopTableFullTrap NOTIFICATION-TYPE
    OBJECTS 	  {
			rcIpv6FhsSnoopNotificationEntryType,
			rcIpv6FhsSnoopNotificationEntryCount
		  }
    STATUS 	  current
    DESCRIPTION   "This trap is generated whenever static or dynamic binding 
		  entry count has reached their max number. 
		  rcDhcpv6SnoopingNotificationBindingEntryType 
		  indicates the type of entries reached the max number"
    ::= { rcTrapsMib 321 }

rcnMulticastLaneLimitReachedTrap NOTIFICATION-TYPE
    OBJECTS 	  {
			rcMcastNotificationStreamCountSlot,
			rcMcastNotificationStreamCountLane
		  }
    STATUS 	  current
    DESCRIPTION   "A rcnMulticastLaneLimitReachedTrap signifies that the
		   multicast stream limit is crossed for the particular
		   lane in the slot."
    ::= { rcTrapsMib 322 }

rcnLicenseWillExpire NOTIFICATION-TYPE
        OBJECTS       {rcLicenseFileName, rcLicenseDaysLeftBeforeExpiration}	
        STATUS        current
        DESCRIPTION  "This notification signifies the time remaining before
	               Time Based License expires in days."
        ::= { rcTrapsMib 323 }
	
rcnLicenseExpired NOTIFICATION-TYPE
        OBJECTS      {rcLicenseFileName,rcLicenseDaysAfterExpiration}
        STATUS        current
        DESCRIPTION  "A rcnLicenseTrialPeriodExpired signifies that
                      has expired in days."
        ::= { rcTrapsMib 324 }

rcnMsdpMaxSACacheWarnSetTrap    NOTIFICATION-TYPE
   OBJECTS     { rcMsdpVrfId,
                 rcMsdpSACacheType
               }
   STATUS      current
   DESCRIPTION    "This event is generated when the SA entries in the cache database
        exceeds 85 % of maximum value (6K) in local cache or in foreign cache."
    ::= {rcTrapsMib 325}

rcnMsdpMaxSACacheWarnClearTrap    NOTIFICATION-TYPE
   OBJECTS     { rcMsdpVrfId,
                 rcMsdpSACacheType
               }
   STATUS      current
   DESCRIPTION    "This event is generated when the Sa entries in the cache database
        drops to 80 % of the maximum value (6K)."
    ::= {rcTrapsMib 326}

rcnMsdpMaxSACacheErrorSetTrap    NOTIFICATION-TYPE
   OBJECTS     {  rcMsdpVrfId,
                  rcMsdpSACacheType
               }
   STATUS      current
   DESCRIPTION    "This event is generated when the SA entries in the cache database
         hits 100 % of the maximum value (6K)."
    ::= {rcTrapsMib 327}

rcnMsdpMaxSACacheErrorClearTrap    NOTIFICATION-TYPE
   OBJECTS     { rcMsdpVrfId,
                 rcMsdpSACacheType
               }
   STATUS      current
   DESCRIPTION    "This event is generated when the SA entries in the cache database
        drops to 95% of the maximum value."
    ::= {rcTrapsMib 328}

rcnMsdpMaxPeerSACacheWarnSetTrap    NOTIFICATION-TYPE
   OBJECTS     { rcMsdpVrfId,
                 rcMsdpPeerSALimit
               }
   STATUS      current
   DESCRIPTION    "This event is generated when the SA entries for this peer exceeds
        85 % of maximum value configured for this peer."
    ::= {rcTrapsMib 329}

rcnMsdpMaxPeerSACacheWarnClearTrap    NOTIFICATION-TYPE
   OBJECTS     { rcMsdpVrfId,
                 rcMsdpPeerSALimit
               }
   STATUS      current
   DESCRIPTION    "This event is generated when the SA entries for this peer drops to
        80 % of the maximum value configured for this peer."
    ::= {rcTrapsMib 330}

rcnMsdpMaxPeerSACacheErrorSetTrap     NOTIFICATION-TYPE
   OBJECTS     { rcMsdpVrfId,
                 rcMsdpPeerSALimit
               }
   STATUS      current
   DESCRIPTION    "This event is generated when the SA entries for this peer hits 100 %
        of the peer SA limit."
    ::= {rcTrapsMib 331}

rcnMsdpMaxPeerSACacheErrorClearTrap    NOTIFICATION-TYPE
   OBJECTS     { rcMsdpVrfId,
                 rcMsdpPeerSALimit
               }
   STATUS      current
   DESCRIPTION    "This event is generated when the SA entries for this peer drops to 95%
        of the peer SA limit."
    ::= {rcTrapsMib 332}

rcnMsdpEstablishedTrap NOTIFICATION-TYPE
    OBJECTS { rcMsdpVrfId,
              msdpPeerFsmEstablishedTransitions
                    }
    STATUS     current
    DESCRIPTION    "The MSDP Established event is generated when the MSDP FSM
            enters the ESTABLISHED state."
    ::= { rcTrapsMib 333 }

rcnMsdpBackwardTransitionTrap NOTIFICATION-TYPE
    OBJECTS { rcMsdpVrfId,
              msdpPeerState
             }
    STATUS     current
    DESCRIPTION    "The MSDPBackwardTransition Event is generated when the
            MSDP FSM moves from a higher-numbered state to a
            lower-numbered state."
    ::= { rcTrapsMib 334 }

rcnSystemUsbInternalAccessErrorTrap NOTIFICATION-TYPE
        STATUS          current
        DESCRIPTION     "This trap is generated whenever system usb encounters an internal ccess errors "
        ::= { rcTrapsMib 335 }

rcnDigitalCertStatusTrap NOTIFICATION-TYPE
        OBJECTS      { rcDigitalCertStatus }
        STATUS       current
        DESCRIPTION  "A rcDigitalCertStatusTrap signifies the status of
                      Subject Certificate has changed"
        ::= { rcTrapsMib 336 }
    
rcnLicenseNotGranted NOTIFICATION-TYPE
        OBJECTS      {rc2kCardIndex}
        STATUS        current
        DESCRIPTION  "The rcnLicenseNotGranted trap is generated when the license was not granted for
	              specified slot because not enough IOC-BASE entitlements in the license file."
        ::= { rcTrapsMib 337 }

rcnLicenseNotLoaded NOTIFICATION-TYPE
        OBJECTS      {rcLicenseFileName}
        STATUS        current
        DESCRIPTION  "The rcnLicenseNotLoaded trap is generated when the license file failed to load."
        ::= { rcTrapsMib 338 }

rcnLicenseDowngraded NOTIFICATION-TYPE
        OBJECTS      {rcLicenseFileName}
        STATUS        current
        DESCRIPTION  "The rcnLicenseDowngraded trap is generated when the license file downgraded
	              from feature-pack L3V or L3V-WITH-MACSEC to IOC-BASE."
        ::= { rcTrapsMib 339 }

rcnChasPowerSupplyRunningNormal NOTIFICATION-TYPE
        STATUS        current
        DESCRIPTION  "A rcnChasPowerSupplyRunningNormal signifies that
                     the chassis has recovered from low power supply."
        ::= { rcTrapsMib 340 }


rcnDvrVistPeerDomainMismatchErrorTrap NOTIFICATION-TYPE
        OBJECTS          { rcIsisPeerVirtualBmac }
        STATUS           current
        DESCRIPTION     "This trap is generated whenever V-IST link comes up between 
	    	         two DVR peers that are in different DVR domains."
        ::= { rcTrapsMib 341 }

rcnDvrVistPeerDomainMismatchErrorClearTrap NOTIFICATION-TYPE
        OBJECTS          { rcIsisPeerVirtualBmac }
        STATUS           current
        DESCRIPTION     "This trap is generated whenever the erroneous condition of 
	                 having a V-IST link up between two DVR peers from different
			 DVR domains is cleared."
        ::= { rcTrapsMib 342 }

rcnIsisPlsbStackableDisableIsisTrap NOTIFICATION-TYPE
        OBJECTS       { rcIsisLocalSysId,
                        rcIsisLocalHostName,
                        rcIsisLocalChassisMac,
                        rcIsisRemoteHostName,
                        rcIsisRemoteChassisMac,
                        rcIsisPlsbTrapType,
                        rcIsisTrapIndicator }
        STATUS        current
        DESCRIPTION   "A PLSB ISIS trap signifies that a stack fragment node is 
                       detected with same system-id and nickname as the local node.
                       ISIS disabled globally."
        ::= { rcTrapsMib 343 }

rcnRadiusEapRAVError NOTIFICATION-TYPE
        OBJECTS {
            rcRadiusEapRAVErrorMacAddress,
            rcRadiusEapRAVErrorPort
        }
        STATUS current
        DESCRIPTION
                "This notification indicates that an Eap/Neap client MAC address was
                 authorized on a port, but the port could not be moved to the
                 Radius-Assigned VLAN."
        ::= { rcTrapsMib 344 }

rcnRadiusEapServersDown NOTIFICATION-TYPE
        STATUS      current
        DESCRIPTION
                "This notification is generated when all EAP Radius servers become unreachable."
        ::= { rcTrapsMib 345 }

rcnRadiusEapServerUp NOTIFICATION-TYPE
        OBJECTS   { rcRadiusEapServAddressType,
                    rcRadiusEapServAddress }
        STATUS      current
        DESCRIPTION
                "This notification is generated when at least one EAP Radius server becomes reachable."
        ::= { rcTrapsMib 346 }

rcnIpv6MaxRouteWarnClear NOTIFICATION-TYPE
        OBJECTS      { rcVrfName }
        STATUS        current
        DESCRIPTION  "A rcnIpv6MaxRouteWarnClear trap signifies that
                     the number of ipv6 routes in the routing table of
                     the Virtual Router has droped below its
                     warning threshold."
        ::= { rcTrapsMib 347 }

rcnIpv6MaxRouteWarnSet NOTIFICATION-TYPE
        OBJECTS      { rcVrfName }
        STATUS        current
        DESCRIPTION  "A rcnIpv6MaxRouteWarnSet trap signifies that
                     the given Virtual Routers routing table is 
                     reaching its maximum size. Action should be
                     taken to prevent this"
        ::= { rcTrapsMib 348 }

rcnIpv6MaxRouteDropClear NOTIFICATION-TYPE
        OBJECTS      { rcVrfName }
        STATUS        current
        DESCRIPTION  "A rcnIpv6MaxRouteDropClear signifies that
                     the given Virtual Routers routing table is 
                     no longer dropping new routes as it is below
                     its maximum size."
        ::= { rcTrapsMib 349 }

rcnIpv6MaxRouteDropSet NOTIFICATION-TYPE
        OBJECTS      { rcVrfName }
        STATUS        current
        DESCRIPTION  "A rcnIpv6MaxRouteDropSet trap signifies that
                     the given Virtual Routers routing table has
                     reached its maximum size, and is now dropping
                     all new non static routes."
        ::= { rcTrapsMib 350 }

rcnIsisPlsbIsisEnabledWithZeroNicknameTrap  NOTIFICATION-TYPE
        OBJECTS       { rcIsisLocalSysId,
                        rcIsisPlsbTrapType,
                        rcIsisTrapIndicator}
        STATUS        current
        DESCRIPTION   "A PLSB ISIS trap signifies that ISIS was enabled with Zero Nickname."
        ::= { rcTrapsMib 351 }

-- Removing from BOSS version of this file for being unsupported
-- rcnRestconfServerOperationStatusTrap  NOTIFICATION-TYPE
--        OBJECTS       { rcRestConfServerOperationStatus }
--        STATUS        current
--        DESCRIPTION   "A trap signifies that the RestConf Server operational status when RestConf 
--                       server is enable and disabled "
--        ::= { rcTrapsMib 352 }

    
-- IMPORTANT NOTE:  The following section contains older definitions of
--                  notifications that do not follow the standard format
--                  for OIDs for notifications.  New notifications should
--                  *NOT* be added to this section.  Instead, they should
--                  be added above, under the snmpTrapsMib branch.
--

rcCardDown NOTIFICATION-TYPE
        OBJECTS      { rcCardIndex, rcCardAdminStatus, rcCardOperStatus }
        STATUS       current
        DESCRIPTION  "A rcCardDown trap signifies that the SNMPv2 entity,
                     acting in an agent role, has detected that the
                     rcCardOperStatus object for one of its cards 
                     is about to transition into the down state."
        ::= { rcTraps 1 }

rcCardUp NOTIFICATION-TYPE
        OBJECTS       { rcCardIndex, rcCardAdminStatus, rcCardOperStatus }
        STATUS        current
        DESCRIPTION   "A rcCardUp trap signifies that the SNMPv2 entity,
                      acting in an agent role, has detected that the
                      rcCardOperStatus object for one of its cards 
                      is about to transition into the up state."
        ::= { rcTraps 2 }

rcErrorNotification NOTIFICATION-TYPE
        OBJECTS       { rcErrorLevel, rcErrorCode, rcErrorText }
        STATUS        current
        DESCRIPTION   "A rcErrorNotification trap signifies that the 
                      SNMPv2 entity, acting in an agent role, has 
                      detected that an error condition has occured."
        ::= { rcTraps 3 }
 
rcStpNewRoot NOTIFICATION-TYPE
        OBJECTS       { rcStgId }
        STATUS        current
        DESCRIPTION   "A rcStpNewRoot trap signifies that the
                      SNMPv2 entity, acting in an agent role, has
                      detected the Spanning Tree Protocol has declared
                      the device to be the new root of the spanning 
       		      tree." 
        ::= { rcTraps 4 }

rcStpTopologyChange NOTIFICATION-TYPE
       OBJECTS        { rcStgId, rcPortIndex }
       STATUS         current   
       DESCRIPTION    "A rcStpTopologyChange trap signifies that the 
                      SNMPv2 entity, acting in an agent role, has 
                      detected the Spanning Tree Protocol has gone due
                      a topology change event."
       ::= { rcTraps 5 }

rcChasPowerSupplyDown NOTIFICATION-TYPE
        OBJECTS       { rcChasPowerSupplyId, rcChasPowerSupplyOperStatus}
        STATUS        current
        DESCRIPTION   "A rcChasPowerSupplyDown trap signifies that the 
                      SNMPv2 entity, acting in an agent role, has 
                      detected that the rcChasPowerSupplyOperStatus 
                      object for one of its power supply unit is 
                      about to transition into the down state."
        ::= { rcTraps 6 }

rcChasFanDown NOTIFICATION-TYPE
        OBJECTS       { rcChasFanId, rcChasFanOperStatus}
        STATUS        current
        DESCRIPTION   "A rcChasFanDown trap signifies that the 
                      SNMPv2 entity, acting in an agent role, has 
                      detected that the rcChasFanOperStatus object 
                      for one of its power supply unit is about to 
                      transition into the down state."
        ::= { rcTraps 7 }

rcLinkOscillation NOTIFICATION-TYPE
        OBJECTS          { rcPortIndex }
        STATUS             current
        DESCRIPTION   "A rcLinkOscillation trap signifies that the
                       SNMPv2 entity, acting in an agent role, has
                       detected an excessive number of link state
                       transitions on the specified port."
        ::= { rcTraps 8 }

rcMacViolation NOTIFICATION-TYPE	
        OBJECTS       { rcErrorText, rcPortIndex }
        STATUS        current
        DESCRIPTION   "A rcMacViolation trap signifies that the
                      SNMPv2 entity, acting in an agent role, has
                      received a PDU with an invalid source MAC
                      address."
        ::= { rcTraps 9 }

rcSonetTrap NOTIFICATION-TYPE
        OBJECTS       { rcPortIndex, rcPosSonetTrapType, rcPosSonetTrapIndication }
        STATUS        current
        DESCRIPTION   "A rcSonetTrap trap signifies that the
                      SNMPv2 entity, acting in an agent role, has
                      detected a change of status on a Sonet port."
        ::= { rcTraps 10 }

rc2kCardDown NOTIFICATION-TYPE
        OBJECTS      { rc2kCardIndex, 
                       rc2kCardFrontAdminStatus, 
                       rc2kCardFrontOperStatus }
        STATUS       obsolete
        DESCRIPTION  "A rcCardDown trap signifies that the SNMPv2 entity,
                     acting in an agent role, has detected that the
                     rcCardOperStatus object for one of its cards
                     is about to transition into the down state."
        ::= { rcTraps 11 }

rc2kCardUp NOTIFICATION-TYPE
        OBJECTS       { rc2kCardIndex, 
                        rc2kCardFrontAdminStatus, 
                        rc2kCardFrontOperStatus }
        STATUS        obsolete
        DESCRIPTION   "A rcCardUp trap signifies that the SNMPv2 entity,
                      acting in an agent role, has detected that the
                      rcCardOperStatus object for one of its cards
                      is about to transition into the up state."
        ::= { rcTraps 12 }

rc2kTemperature NOTIFICATION-TYPE
        OBJECTS       { rc2kChassisTemperature }
        STATUS        current
        DESCRIPTION   "A rc2kTemperature trap signifies that the SNMPv2 
		      entity, acting in an agent role, has detected the
                      chassis is over-heating."
        ::= { rcTraps 13 }

rcChasPowerSupplyUp NOTIFICATION-TYPE
        OBJECTS       { rcChasPowerSupplyId, rcChasPowerSupplyOperStatus}
        STATUS        current
        DESCRIPTION   "A rcChasPowerSupplyUp trap signifies that the
                      SNMPv2 entity, acting in an agent role, has
                      detected that the rcChasPowerSupplyOperStatus
                      object for one of its power supply unit is
                      about to transition into the up state."
        ::= { rcTraps 14 }

rc2kAtmPvcLinkStateChange NOTIFICATION-TYPE
        OBJECTS       { rc2kAtmPvcIfIndex, 
                        rc2kAtmPvcVpi, 
                        rc2kAtmPvcVci, 
                        rc2kAtmPvcOamVcStatus }    
        STATUS        current
        DESCRIPTION   "A rc2kAtmPvcLinkStateChange trap signifies that the 
                       SNMPv2 entity, acting in an agent role, has detected 
                       that the rc2kAtmPvcOamVcStatus object for one of PVC is
                       about to transition into different state, either from 
                       up to down or from down to up."
        ::= { rcTraps 15 } 

rcStpTCN NOTIFICATION-TYPE
       OBJECTS        { rcStgId, rcPortIndex, rcStgBridgeAddress }
       STATUS         current
       DESCRIPTION    "A rcStpTopologyChange trap signifies that the
                      SNMPv2 entity, acting in an agent role, has
                      detected the Spanning Tree Protocol has gone due
                      a topology change event."
       ::= { rcTraps 16 }

rcSmltIstLinkUp NOTIFICATION-TYPE
        STATUS        current
        DESCRIPTION   "A rcSmltIstLinkUp trap signifies that the split
                      MLT link is from down to up."
        ::= { rcTraps 17 }

rcSmltIstLinkDown NOTIFICATION-TYPE
        STATUS        current
        DESCRIPTION   "A rcSmltIstLinkDown trap signifies that the
                      split MLT link is from up to down."
        ::= { rcTraps 18 }

rcSmltLinkUp NOTIFICATION-TYPE
        OBJECTS       { rcMltSmltId }
        STATUS        current
        DESCRIPTION   "A rcMltSmltId trap signifies that the split 
                      SMLT link is up."
        ::= { rcTraps 19 }

rcSmltLinkDown NOTIFICATION-TYPE
        OBJECTS       { rcMltSmltId }
        STATUS        current
        DESCRIPTION   "A rcMltSmltId trap signifies that the split 
                      SMLT link is down."
        ::= { rcTraps 20 }

rcChasFanUp NOTIFICATION-TYPE
        OBJECTS       { rcChasFanId, rcChasFanOperStatus}
        STATUS        current
        DESCRIPTION   "A rcChasFanUp trap signifies that the
                      SNMPv2 entity, acting in an agent role, has
                      detected that the rcChasFanOperStatus object
                      for one of its power supply unit is about to
                      transition into the up state."
        ::= { rcTraps 21 }

rcPasswordChange NOTIFICATION-TYPE
        OBJECTS       { rcCliPasswordChange, rcCliPassChangeResult}
        STATUS        current
        DESCRIPTION   "A rcPasswordChange trap signifies that the
                      SNMPv2 entity, acting in an agent role, has
                      detected that the one of the cli password is
                      changed."
        ::= { rcTraps 22 }

rcEmError NOTIFICATION-TYPE
        OBJECTS       { rc2kCardIndex, rcChasEmModeError}
        STATUS        current
        DESCRIPTION   "A rcEmError trap signifies that the
                      SNMPv2 entity, acting in an agent role, has
                      detected Em error."
        ::= { rcTraps 23 }

rcVpnTrap NOTIFICATION-TYPE
        OBJECTS       { rcVpnVpnId, rcErrorText, rcVpnTunnelLspId,
                        rcIpMplsGlobalRouterId, rcVpnRemotePeerId, 
                        rcSyslogHostSeverity}    
        STATUS        current
        DESCRIPTION   "L2Vpn will send trap when the Lsp goes down, which
                       would affect the operational status of the Vpn (given
                       by the VpnId). The Cause will indicate the reason for
                       sending the trap. It can either LSP down/failure or
                       to the bandwidth requirements cannot be fulfilled.
                       Severity Level can be Warning/Error/Fatal."
        ::= { rcTraps 24 }

rcPcmciaCardRemoved NOTIFICATION-TYPE
        STATUS        current
        DESCRIPTION   "A rcPcmciaRemoved trap signifies that the
                      SNMPv2 entity, acting in an agent role, has
                      detected that the PCMCIA card is being removed."
        ::= { rcTraps 25 }

rcSmartCpldTimerFired NOTIFICATION-TYPE
        OBJECTS       { rc2kCardIndex }
        STATUS        current
        DESCRIPTION   "A rcSmartCpldTimerFired trap signifies that the
                       cpld timer fired."
        ::= { rcTraps 26 }

rcCardCpldNotUpDate NOTIFICATION-TYPE
        OBJECTS       { rc2kCardIndex }
        STATUS        current
        DESCRIPTION   "A rcCardCpldNotUpDate trap signifies that the
                       cpld is not up to date."
        ::= { rcTraps 27 }

rcIgapLogFileFull NOTIFICATION-TYPE
        STATUS        current
        DESCRIPTION   "A rcIgapLogFileFull trap signifies that the
                       Igap accounting time-out Log File reach the 
                       maximum."
        ::= { rcTraps 28 }

rcCpLimitShutDown NOTIFICATION-TYPE
        OBJECTS       { rcPortIndex, 
                        ifAdminStatus,
                        ifOperStatus,
                        rcPortCpLimitShutDown } 
        STATUS        current
        DESCRIPTION   "A rcCpLimitShutDown trap signifies that the
                       cp limit for the port is shutting down."
        ::= { rcTraps 29 }

rcSshServerEnabled NOTIFICATION-TYPE
        OBJECTS       { rcSshGlobalPort }
        STATUS        current
        DESCRIPTION   "A rcSshServerEnabled trap signifies that the
                       SSH server is enabled."
        ::= { rcTraps 30 }

rcSshServerDisabled NOTIFICATION-TYPE
        OBJECTS       { rcSshGlobalPort }
        STATUS        current
        DESCRIPTION   "A rcSshServerDisabled trap signifies that the
                       SSH server is disabled."
        ::= { rcTraps 31 }

rcSshSessionLogin NOTIFICATION-TYPE
        OBJECTS       { rcSshGlobalHostIpAddr }
        STATUS        current
        DESCRIPTION   "A rcSshSessionLogin trap signifies that there
                       is a SSH session login."
        ::= { rcTraps 32 }

rcSshSessionLogout NOTIFICATION-TYPE
        OBJECTS       { rcSshGlobalHostIpAddr }
        STATUS        current
        DESCRIPTION   "A rcSshSessionLogout trap signifies that there
                       is a SSH session logout."
        ::= { rcTraps 33 }

rcSshUnauthorizedAccess NOTIFICATION-TYPE
        OBJECTS       { rcSshGlobalHostIpAddr }
        STATUS        current
        DESCRIPTION   "A rcSshUnauthorizedAccess trap signifies that
                       an unauthorized access has occured."
        ::= { rcTraps 34 }

rcHaCpuState NOTIFICATION-TYPE
        OBJECTS       { rc2kCardIndex, rcL2RedundancyHaCpuState }
        STATUS        current
        DESCRIPTION   "A rcHaCpuState trap signifies that the
                       state of the HA-CPU."
        ::= { rcTraps 35 }

rcInsufficientMemory NOTIFICATION-TYPE
        OBJECTS       { rc2kCardIndex}
        STATUS        current
        DESCRIPTION   "A rcInsufficientMemory trap indicates insufficient memory on
                       CPU blade for proper operation. Recommended memory = 256 MB 
                       available through Nortel Networks upgrade kit"
        ::= { rcTraps 36 }

rcSaveConfigAction NOTIFICATION-TYPE
        OBJECTS       { rcSysAction }
        STATUS        current
        DESCRIPTION   "A rcSaveConfigAction trap indicates the switch run
                       time or boot configuration is being saved"
        ::= { rcTraps 37 }

rcLoopDetectOnPort NOTIFICATION-TYPE
        OBJECTS       { rcVlanId, rcPortIndex }
        STATUS        current
        DESCRIPTION   "A rcSaveConfigAction trap indicates that a loop has
                       been detected on a port. The vlan on that port will
                       be disabled."
        ::= { rcTraps 38 }

rcbgpEstablished NOTIFICATION-TYPE
        OBJECTS { rcIpBgpPeerIpAddress, rcIpBgpPeerLastError, rcIpBgpPeerState }
        STATUS  current
        DESCRIPTION "The BGP Established event is generated when
                 the BGP FSM enters the ESTABLISHED state."
        ::= { rcTraps 39 }

rcbgpBackwardTransition NOTIFICATION-TYPE
        OBJECTS { rcIpBgpPeerIpAddress, rcIpBgpPeerLastError, rcIpBgpPeerState }
        STATUS  current
        DESCRIPTION "The BGPBackwardTransition Event is generated
                 when the BGP FSM moves from a higher numbered
                 state to a lower numbered state."
        ::= { rcTraps 40 }

rcAggLinkUp NOTIFICATION-TYPE
        OBJECTS       { rcMltId }
        STATUS        current
        DESCRIPTION   "A rcAggLinkUp trap is generated when the operational
                       state of the aggregator changes from down to up."
        ::= { rcTraps 41 }

rcAggLinkDown NOTIFICATION-TYPE
        OBJECTS       { rcMltId }
        STATUS        current
        DESCRIPTION   "A rcAggLinkDown trap is generated when the operational
                       state of the aggregator changes from up to down."
        ::= { rcTraps 42 }

rcIgmpNewGroupMember NOTIFICATION-TYPE
        OBJECTS       { rcIgmpGroupIfIndex, rcIgmpGroupIpAddress, rcIgmpGroupInPort,
                                      rcIgmpGroupMembers }
        STATUS        current
        DESCRIPTION   "An IgmpNewGroupMember  trap signifies that a
                       new member has come on an interface."
        ::= { rcTraps 43 }

rcIgmpLossGroupMember NOTIFICATION-TYPE
        OBJECTS       { rcIgmpGroupMembers, rcIgmpGroupIpAddress, rcIgmpGroupInPort,
                                      rcIgmpGroupIfIndex }
        STATUS        current
        DESCRIPTION   "An IgmpLossGroupMember  trap signifies that a
                       group member has been lost on an interface."
        ::= { rcTraps 44 }

rcIgmpNewQuerier NOTIFICATION-TYPE
-- cannot include igmpInterfaceIfIndex in the OBJECTS clause because it
-- is not-accessible
--        OBJECTS       { igmpInterfaceIfIndex, igmpInterfaceQuerier }
        STATUS        obsolete
        DESCRIPTION   "An igmpNewQuerier trap signifies that a new
                       querier has come up on an interface."
        ::= { rcTraps 45 }

rcIgmpQuerierChange NOTIFICATION-TYPE
-- cannot include igmpInterfaceIfIndex in the OBJECTS clause because it
-- is not-accessible
--        OBJECTS       { igmpInterfaceIfIndex,
--                        rcIgmpInterfaceExtnNewQuerier,
--                        igmpInterfaceQuerier }
        STATUS        obsolete
        DESCRIPTION   "An rcIgmpQuerierChange trap signifies that
                       the querier has changed."
        ::= { rcTraps 46 }

rcDvmrpIfStateChange NOTIFICATION-TYPE
-- Cannot use these, as they are either not-accessible, or no longer exist
-- in the current draft of the DVMRP-STD-MIB
--        OBJECTS       { dvmrpInterfaceIfIndex, dvmrpInterfaceOperState }
        STATUS        current
        DESCRIPTION   "A rcDvmrpIfStateChange trap signifies that there
                       has been a change in the state of a DVMRP
                       interface."
        ::= { rcTraps 47 }

rcDvmrpNewNbrChange NOTIFICATION-TYPE
-- Cannot use these, as they are either not-accessible, or no longer exist
-- in the current draft of the DVMRP-STD-MIB
--        OBJECTS       { dvmrpNeighborIfIndex, dvmrpNeighborAddress }
        STATUS        current
        DESCRIPTION   "A rcDvmrpNewNbrChange trap signifies that a new
                       neighbor has come up on a DVMRP interface."
        ::= { rcTraps 48 }

rcDvmrpNbrLossChange NOTIFICATION-TYPE
-- Cannot use these, as they are either not-accessible, or no longer exist
-- in the current draft of the DVMRP-STD-MIB
--        OBJECTS       { dvmrpNeighborIfIndex, dvmrpNeighborAddress }
        STATUS        current
        DESCRIPTION   "A rcDvmrpNbrLossChange trap signifies that a new
                       neighbor has gone down on a DVMRP interface."
        ::= { rcTraps 49 }

rcPsePortOnOff  NOTIFICATION-TYPE
        OBJECTS       { rcPortPoePseIndexGroupIndex,
                        rcPortPoePseIndexPortIndex,
                        pethPsePortDetectionStatus }
        STATUS        current
        DESCRIPTION   "A rcPsePortOnOff trap signifies that if Pse Port is delivering or not power to the
                   This Notification SHOULD be sent on every status change except in the searching mode."
        ::= { rcTraps 50 }

rcPsePortPowerMaintenanceStatus  NOTIFICATION-TYPE
-- pethPsePortPowerMaintenanceStatus no longer exists, cannot use it here
--        OBJECTS       { rcPortPoePseIndexGroupIndex,
--                        rcPortPoePseIndexPortIndex,
--                        pethPsePortPowerMaintenanceStatus }
        OBJECTS       { rcPortPoePseIndexGroupIndex,
                        rcPortPoePseIndexPortIndex }
        STATUS        current
        DESCRIPTION   "A rcPsePortPowerMaintenanceStatus trap signifies that a Port change Status
                                          and it SHOULD be sent on every status change."
        ::= { rcTraps 51 }

rcMainPseBackupActivate  NOTIFICATION-TYPE
-- pethMainPseBackupActivated no longer exists, cannot use it here
--        OBJECTS       { rcPortPoePseIndexGroupIndex,
--                        rcPortPoePseIndexPortIndex,
--                        pethMainPseBackupActivated }
        OBJECTS       { rcPortPoePseIndexGroupIndex,
                        rcPortPoePseIndexPortIndex }
        STATUS        current
        DESCRIPTION   "A rcMainPseBackupActivate trap signifies that
                       a Backup is Activated or BackUp is released on a Pse Port Group."
        ::= { rcTraps 52 }

rcMainPowerUsageOn  NOTIFICATION-TYPE
        OBJECTS       { rcPortPoePseIndexGroupIndex, pethMainPseConsumptionPower }
        STATUS        current
        DESCRIPTION   "A rcMainPowerUsageOn trap signifies that PSE Threshold Usage indication
                                          of a PSE Port Group is on, the usage power is above the threshold."
        ::= { rcTraps 53 }

rcMainPowerUsageOff  NOTIFICATION-TYPE
        OBJECTS       { rcPortPoePseIndexGroupIndex, pethMainPseConsumptionPower }
        STATUS        current
        DESCRIPTION   "A rcMainPowerUsageOn trap signifies that PSE Threshold Usage indication
                                           of a PSE Port Group is off, the usage power is above the threshold."
        ::= { rcTraps 54 }

rcPseCardOnOff NOTIFICATION-TYPE
        OBJECTS       { rcPortPoeMainPseExtnPwrAdmin }
        STATUS        current
        DESCRIPTION   "A rcPoeMainPwrFailure trap signifies that the main power admin status is up."
        ::= { rcTraps 55 }

rcTlsWatermarkTrap  NOTIFICATION-TYPE
        OBJECTS       { rcTlsTdiEndptTdId, rcTlsTdiEndptUniAddr, rcTlsEndptWatermarkIndication}
        STATUS        current
        DESCRIPTION   "A Watermark trap signifies that the Mac Table for the
                       endpoint has reached its high watermark or is already full."
        ::= { rcTraps 56 }

rcTdcTestResultTrap  NOTIFICATION-TYPE
        OBJECTS       { rcTlsTestTdcTestId, rcTlsTdcTestResultIndication }
        STATUS        current
        DESCRIPTION   "A Tdc test fail trap indicates that the tdc test test identified by test ID failed."
        ::= { rcTraps 57 }

rcTdcTestRttExceedTrap  NOTIFICATION-TYPE
        OBJECTS       { rcTlsTestTdcTestId, rcTlsTdcTestRttExceedIndication }
        STATUS        current
        DESCRIPTION   "A Tdc Rtt Exceed trap indicates that the round trip
                       time of the tdc test identified by test ID exceeded the configured threshold value."
        ::= { rcTraps 58 }
        
rcIgmpNewQuerierOnIf NOTIFICATION-TYPE
        OBJECTS       { rcIgmpInterfaceIfIndex, rcIgmpInterfaceQuerier }
        STATUS        current
        DESCRIPTION   "An igmpNewQuerier trap signifies that a new
                       querier has come up on an interface."
        ::= { rcTraps 121 }

rcIgmpQuerierChanged NOTIFICATION-TYPE
        OBJECTS       { rcIgmpInterfaceIfIndex,
                        rcIgmpInterfaceExtnNewQuerier,
                        rcIgmpInterfaceQuerier }
        STATUS        current
        DESCRIPTION   "An rcIgmpQuerierChange trap signifies that
                       the querier has changed."
        ::= { rcTraps 122 }

rcDuplexMismatch NOTIFICATION-TYPE
        OBJECTS       { rcPortIndex,lldpRemPortIdSubtype,lldpRemPortId }
        STATUS        current
        DESCRIPTION   "A rcDuplexMismatch trap signifies that
                       a LLDP Neighbor Port's Duplex/Speed mismatches
                       with local port"
        ::= { rcTraps  123 }

END
