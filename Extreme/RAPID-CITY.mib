RAPID-CITY DEFINITIONS ::= BEGIN

IMPORTS
    MODULE-IDENTITY, OBJECT-TYPE, Gauge32, Unsigned32, Counter32, Integer32,
    enterprises, IpAddress, TimeTicks
        FROM SNMPv2-SMI
    TEXTUAL-CONVENTION, RowStatus, TruthValue, MacAddress, DisplayString,
    DateAndTime, TimeInterval, TimeStamp
        FROM SNMPv2-TC
    InterfaceIndex
        FROM IF-MIB
    SnmpAdminString, SnmpSecurityModel
        FROM SNMP-FRAMEWORK-MIB
    InetAddressType, InetAddress, InetAddressPrefixLength,
    InetAutonomousSystemNumber
        FROM INET-ADDRESS-MIB
    LldpPortIdSubtype, LldpPortId, lldpRemEntry, LldpManAddress, LldpSystemCapabilitiesMap
        FROM LLDP-MIB	
    Ipv6Address
        FROM IPV6-TC
    AddressFamilyNumbers
        FROM IANA-ADDRESS-FAMILY-NUMBERS-MIB;

rapidCity MODULE-IDENTITY
       LAST-UPDATED     "201810100000Z"
       ORGANIZATION 	"Avaya"
       CONTACT-INFO 	"Avaya
                       	 4655 Great America Parkway 
                         Santa Clara, CA 95052-8185"
		     
       DESCRIPTION      "Enterprise MIB for the Accelar product family."

       REVISION "201810100000Z" -- 10 Oct  2018
       DESCRIPTION "Version 246: Added rcWebROEnable"

       REVISION "201809260000Z" -- 26 September  2018
       DESCRIPTION "Version 245:  Add rcSysDefaultPingTracerouteContextType and
	   			  rcSysDefaultPingTracerouteContextVrfName.
				  Requested by Julie Carleton (Prem)"

       REVISION "201808100000Z" -- 10 August  2018
       DESCRIPTION "Version 244:  Added enueration label dynamic(3) to
	   			 rcSysDnsServerListType"

       REVISION "201808100000Z" -- 10 August 2018
       DESCRIPTION "Version 243: Added rcChasType a4624GTSPWRPLUS and  
	   			a4648GTSPWRPLUS"

       REVISION "201807270000Z" -- 27 July 2018
       DESCRIPTION "Version 242: Add rcSysLocatorLed
	   			 Requested by Jathavedas (Prem)"

       REVISION "201807120000Z" -- 12 July 2018
       DESCRIPTION "Version 241: Change aES6108x32 to a7432CQ. 
	   			 And aES6108x48vx8c to a7456VSC"
                                            
       REVISION "201805220000Z" -- 22 May 2018
       DESCRIPTION "Version 240: Remove rcES6108-32c rcES6108-48v-8c
                                 Added aES6108x32c and aES6108x48vx8c"

       REVISION "201804090000Z" -- 09 April 2018
       DESCRIPTION "Version 239: Added rcES6108-32c rcES6108-48v-8c"
	   
       REVISION "201803060000Z" -- 06 March 2018
       DESCRIPTION "Version 238: Added rcChasPowerSupplyDetailInputOperLineVoltage
	                         rcChasPowerSupplyDetailInputPower"
	   
       REVISION "201802210000Z" -- 21 Feb 2018
       DESCRIPTION "Version 237: Added rcRestConf"
	   
       REVISION "201801170000Z" -- 17 January 2018
       DESCRIPTION "Version 237: Added rcAppTelemetry.
	   			 Requested by Sandu Elena (ppalarapu)"

       REVISION "201711150000Z" -- 15 Nov 2017
       DESCRIPTION "Version 236: Added rcSshcGlobalRekeyDataLimit."

       REVISION "201709190000Z" -- 19 September 2017
       DESCRIPTION "Version 235: Renamed rcCliUserRole to rcCliUserLevel.
	   			 (prempa)"

       REVISION "201709180000Z" -- 18 September 2017
       DESCRIPTION "Version 234: Added rcSyslogGlobalIncludeHostIp and rcOvsdb.
	   			 (prempa)"

       REVISION "201709060000Z" -- 6 September 2017
       DESCRIPTION "Version 233: Added rcCarrier.
	   			 Requested by Vinotha (VSP9K) (prempa)"

       REVISION "201708310000Z" -- 31 August 2017
       DESCRIPTION "Version 232: Added rcCliUserTable.
	   			 Requested by Claudiu Gabriel Mitroi, Levente Dozsa (submit 35924) (prempa)"

       REVISION "201706130000Z" -- 13 June 2017
       DESCRIPTION "Version 231: Added rcNls as {rcMgmt 223}.
	   			 Requested by Mihai Catalin Bleont for
				 Native Linux Stack(NLS) project (prempa)"

       REVISION "201705080000Z" -- 08 May 2017
       DESCRIPTION "Version 230: Added rcVSP5030GSXuPWR and rcVSP5054GSXuPWR
	   			 Requested by Catalin Neacsu (prempa)."

       REVISION "201702240000Z" -- 24 Feb 2017
       DESCRIPTION "Version 229: Added rcSysReservedPower and rcSysRequiredPower
	   			 Submit 32962 (prempa)."

       REVISION "201701310000Z" -- 31 Jan 2017
       DESCRIPTION "Version 228: Corrected MIB compiler errors."
	   
       REVISION "201701120000Z" -- 12 Jan 2017
       DESCRIPTION "Version 227: Added rcLacpGlobalSysId
				 Requested by Ababei Isabella (prempa)"
	   
       REVISION "201611180000Z" -- 18 Nov 2016
       DESCRIPTION "Version 226: Changed rcSshGlobalDsaKeySize from (1024..2048) to
	   			 1024
				 Requested by Hariprasad Rajendran (shchang)" 	   

       REVISION "201610250000Z" -- 25 Oct. 2016
       DESCRIPTION "Version 225: Added 	rcLldpRemExtendedIpAddress"
	   
       REVISION "201610240000Z" -- 24 Oct. 2016
       DESCRIPTION "Version 224:  Added rcLldpRemExtendedTable"
	   
       REVISION "201610130000Z" -- 13 Oct. 2016
       DESCRIPTION "Version 223: Added rcSyslogHostSecureForwardingServerCertName.
	   			 Requested by Hariprasad Rajendran (prempa)"
	   
       REVISION "201610050000Z" -- 05 Oct. 2016
       DESCRIPTION "Version 222: Added rcLogLoggingGlobal"
	   
       REVISION "201609200000Z" -- 20 Sept. 2016
       DESCRIPTION "Version 221: Increased the range of rcWebRWAPassword, 
	   			 rcWebRWPassword, rcWebROPassword,
				 rcWebRWL3Password and rcWebRWL2Password
				 from 1-20 to 1-32.
				 Requested by Hariprasad Rajendran (submit 30398)
                                 (prempa)" 

       REVISION "201609080000Z" -- 08 Sept. 2016
       DESCRIPTION "Version 220: Renamed rcVSP9408 to rcVSP8608.
	   			 Renamed a9408 under rcChasType to a8608
                                 (prempa)" 

       REVISION "201609010000Z" -- 01 Sept. 2016
       DESCRIPTION "Version 219: Changed rcWebPasswordMinimumLength to rcWebMinimumPasswordLength.
                                 (prempa)" 

       REVISION "201609010000Z" -- 01 Sept. 2016
       DESCRIPTION "Version 218: Added softResetCoreDump(14) under rcSysActionRwa.
	                         Requested by Ning Zhong (shchang)"

       REVISION "201608310000Z" -- 31 Aug. 2016
       DESCRIPTION "Version 217: Added rcWebPasswordMinimumLength.
                                 Requested by Hariprasad Rajendran (prempa)" 

       REVISION "201608310000Z" -- 31 Aug. 2016
       DESCRIPTION "Version 216: changed tlsProtec and sshProtect under 
	   			 rcSyslogHostSecureForwardingMode to
				 tls and ssh.
				 Added rcSyslogRootCertificateTable.
                                 Requested by Hariprasad Rajendran (prempa)"   

       REVISION "201608160000Z" -- 16 Aug. 2016
       DESCRIPTION "Version 215: change rcSshGlobalSshClientEnable
                                to rcSshGlobalClientEnable"   
	   
       REVISION "201608100000Z" -- 10 Aug. 2016
       DESCRIPTION "Version 214: added rcSshGlobalSshClientEnable"

       REVISION "201607220000Z" -- 22 July 2016
       DESCRIPTION "Version 213: update rcSshAuthType by removing
	   	                 hmacSha2256(3),
                                 hmacSha2512(4)"
	   
       REVISION "201605270000Z" -- 27 May 2016
       DESCRIPTION "Version 212: Added rcDigitalCert as {rcMgmt 222}.
	   			 Requested by Hari Prasad Rajendran
				 For CC Release Digital Certificates
				 Submit 27779 (prempa)"
	   
       REVISION "201605260000Z" -- 26 May 2016
       DESCRIPTION "Version 211: Added rcWebTlsMinimumVersion"
	   
       REVISION "201605230000Z" -- 23 May 2016
       DESCRIPTION "Version 210: Removed hmacSha196 from rcSshAuthType
	   			 Requested by Hariprasad Rajendran (prempa)"
	   
       REVISION "201605090000Z" -- 09 May 2016
       DESCRIPTION "Version 209: Added rcSflow"
	   
       REVISION "201605090000Z" -- 09 May 2016
       DESCRIPTION "Version 208: Extended the range of rcSshGlobalRsaKeySize
	   			 from 512..1024 to 512..2048 (prempa)"
	   
       REVISION "201605090000Z" -- 09 May 2016
       DESCRIPTION "Version 207: Extended the range of rcSshGlobalDsaKeySize
	   			 from 512..1024 to 512..2048.
				 Requested by Hariprasad Rajendran (submit 27837) (prempa)"
	   
       REVISION "201605090000Z" -- 09 May 2016
       DESCRIPTION "Version 206: Changed the syntax of 
	   			 rcSshAuthType, rcSshEncryptionType and
	   			 rcSshKeyExchangeMethod to BITS.
				 Requested by Hariprasad Rajendran (submit 27837) (prempa)"
	   
       REVISION "201605090000Z" -- 09 May 2016
       DESCRIPTION "Version 205: Added rcSshAuthType, rcSshEncryptionType and
	   			 rcSshKeyExchangeMethod.
				 Requested by Hariprasad Rajendran (submit 27837) (prempa)"
	   
       REVISION "201603150000Z" -- 15 Mar. 2016
       DESCRIPTION "Version 204: Added DSG system OID rcDSG9032"
	   
       REVISION "201603020000Z" -- 02 Mar. 2016
       DESCRIPTION "Version 203: Added DSG system OID and rcLldpExt objects"
	   
       REVISION "201603020000Z" -- 02 Mar. 2016
       DESCRIPTION "Version 202: Added rcCliSystemMib"
	   
       REVISION "201601200000Z" -- 20 Jan. 2016
       DESCRIPTION "Version 201: Added rcDvr"
	   
       REVISION "201601040000Z" -- 04 Jan. 2016
       DESCRIPTION "Version 200: Added rcChasBrandName"
	   
       REVISION "201511280000Z" -- 28 Nov. 2015
       DESCRIPTION "Version 199: Added rcVxLan"
	   
       REVISION "201511030000Z" -- 03 Nov. 2015
       DESCRIPTION "Version 198: Added rcChasPartNumber and
	                         rcChasModelName"
      
       REVISION "201510010000Z" -- 07 October 2015
       DESCRIPTION "Version 197: Changed Range rcCliRWL3Password,
	                         rcCliRWL2Password,rcCliRWL1Password,
				 rcCliROPassword
				 Requested by Tarun Shahi (malok)"
			     
       REVISION "201510010000Z" -- 01 October 2015
       DESCRIPTION "Version 196: Increased the range of rcChasFanId 
	   			 from 1..5 to 1..6.
				 Based on submit 25224 (Prem)"
	   
       REVISION "201509210000Z" -- 21 Sept 2015
       DESCRIPTION "Version 195: Added rcSshGlobalKeyboardInteractiveAuth (malok)"
	   
       REVISION "201507210000Z" -- 21 July 2015
       DESCRIPTION "Version 194: Added rcSmtp
				 Requested for NetApp (malok)"
			     
       REVISION "201506260000Z" -- 26 June 2015
       DESCRIPTION "Version 193: Added redSteady and redBlinking values
	   			 under rcChasLedStatus.
				 Requested by Chris Vavruska for NetApp (Prem)"
	   
       REVISION "201506250000Z" -- 25 June 2015
       DESCRIPTION "Version 192: Added rcCliSystem (Prem)"
	   
       REVISION "201506230000Z" -- 23 June 2015
       DESCRIPTION "Version 191: Added rcVossSystem"
	   
       REVISION "201505220000Z" -- 22 May 2015
       DESCRIPTION "Version 190: Replaced rcCdp (not needed anymore) with
	   			 rcPimIpv6.
				 Requested by Cristina/Oana for PIMv6.
				 Submit 23521 (Prem)"
	   
       REVISION "201505190000Z" -- 19 May 2015
       DESCRIPTION "Version 189: Added rcCdp"	   
	   
       REVISION "201504220000Z" -- 22 April 2015
       DESCRIPTION "Version 188: Added rcSshGlobalSftpEnable"	   

       REVISION "201504180000Z" -- 18 April 2015
       DESCRIPTION "Version 187: changed rcL8032 to rcNetApp8032"
	   	   
       REVISION "201504170000Z" -- 17 April 2015
       DESCRIPTION "Version 186: Correctrc rcL8032, a9408 and aNetApp8032"
	   
       REVISION "201504160000Z" -- 16 April 2015
       DESCRIPTION "Version 185: Added rcVSP9408, rcL8032, a9408 and aL8032"
	   
       REVISION "201504140000Z" -- 14 April 2015
       DESCRIPTION "Version 184: Added rcChasPowerSupplyFanFlowType.
	   			 Requested by Pramod, submit 23759 (Prem)"
	   
       REVISION "201504130000Z" -- 13 April 2015
       DESCRIPTION "Version 183: Added rcMRouteIpv6.
	   			 Requested by Cristina for IPv6 MRoute (Prem)"

       REVISION "201504100000Z" -- 10 April 2015
       DESCRIPTION "Version 182: a8404C chassis type"
	   
       REVISION "201504060000Z" -- 06 April 2015
       DESCRIPTION "Version 181: Added rcMld.
	   			 Requested by Stefan for MLD (Prem)"
	   
       REVISION "201504020000Z" -- 02 April 2015
       DESCRIPTION "Version 180: Correction in units to rcSshGlobalRekeyTimeInterval."
	   
       REVISION "201504020000Z" -- 02 April 2015
       DESCRIPTION "Version 179: Added units to rcSshGlobalRekeyTimeInterval.
	   			 Correction in the OID for rcSshGlobalRekeyDataLimit"
	   
       REVISION "201504020000Z" -- 02 April 2015
       DESCRIPTION "Version 178: Added rcSshGlobalRekeyEnable, 
	   			 rcSshGlobalRekeyTimeInterval and
				 rcSshGlobalRekeyDataLimit.
				 Requested by Sahana for changes made
				 as part of a Federal requirement"
	   
       REVISION "201503140000Z" -- 14 March 2015
       DESCRIPTION "Version 177: added rcLogMsgControl"
	   	   	   
       REVISION "201502050000Z" -- 05 Feb 2015
       DESCRIPTION "Version 176: added rcWebInactivityTimeout"
	   	   
       REVISION "201502020000Z" -- 02 Feb 2015
       DESCRIPTION "Version 175: added rcChasFanFlowType For VSP7K"
	   
       REVISION "201412100000Z" -- 10 Dec 2014
       DESCRIPTION "Version 174: Increased the range of rcChasFanId 
	   			 from 1..4 to 1..5.
				 Requested by P.Nandan for changes made in
				 Snowflake (Prem)"
	   
       REVISION "201411050000Z" -- 05 Nov 2014
       DESCRIPTION "Version 173: added VSP4450GXS definition"
	   
       REVISION "201411050000Z" -- 05 Nov 2014
       DESCRIPTION "Version 172: corrected rcVSP7254XSQ and rcVSP7254XTQ
	                         definition"
       REVISION "201410240000Z" -- 24 Oct 2014
       DESCRIPTION "Version 171: added rcASG, rcASGGlobal, 
	   			 rcASGGlobalEnableStatus,
				 rcASGGlobalAccountsTable,
				 rcASGGlobalAFHeader,
				 rcASGGlobalAFHeaderAFID,
				 rcASGGlobalAFHeaderProduct,
				 rcASGGlobalAFHeaderDateAndTime and
				 rcASGGlobalAFHeaderRelease
				 Requested by Pratap Kandregula for 
				 ASG feature on 4K/8K/Avalance (submit 21286).
				 (Prem)"

       REVISION "201410170000Z" -- 17 Oct 2014
       DESCRIPTION "Version 170: added rcSysDnsServerIpv6Addr"
	   	   
       REVISION "201410150000Z" -- 15 Oct 2014
       DESCRIPTION "Version 169: added rcVSP7254XSQ and rcVSP7254XTQ
	                         Added vsp7k7254XSQ and vsp7k7254XTQ
				       to rcChasType
				 Added vsp7k7254XSQ and vsp7k7254XTQ to
				 rcCardType"
	   
       REVISION "201410100000Z" -- 10 Oct 2014
       DESCRIPTION "Version 168: correct  rcIpsec OID"	   

       REVISION "201410090000Z" -- 09 Oct 2014
       DESCRIPTION "Version 167: Added rcIpsec"
	   	   	   
       REVISION "201409090000Z" -- 09 Sept 2014
       DESCRIPTION "Version 166: Added  a8404(1331823105) to rcChasType"
	   	   
       REVISION "201408260000Z" -- 26 August 2014
       DESCRIPTION "Version 165: Added rcLacpGlobalVlacpSeqNumEnable"
	   
       REVISION "201406030000Z" -- 03 June 2014
       DESCRIPTION "Version 164: Added rcChasFanZoneFPGATemperature and 
	   			 rcChasFanZoneFATemperature"
	   
       REVISION "201405140000Z" -- 14 May 2014
       DESCRIPTION "Version 163: Added rcVSP4450GSXPWRPLUS and vsp4k4450GTXHTPWRPLUS.
	                         changed:  a4950GSXPWRPLUS(1231228978) to a4450GSXPWRPLUS(1231228978)"

       REVISION "201404040000Z" -- 04 April 2014
       DESCRIPTION "Version 162: Added rcMACSec"

       REVISION "201404020000Z" -- 02 April 2014
       DESCRIPTION "Version 161: Added dc(5) to
	                         rcChasPowerSupplyDetailInputLineVoltage &
				 rcChasPowerSupplyDetailOperLineVoltage
				 Added notpresent to rcChasFanOperStatus"

       REVISION "201402240000Z" -- 24 Feb 2014
       DESCRIPTION "Version 160: Added ac1100vOr2200v to
	                         rcChasPowerSupplyDetailInputLineVoltage &
				 rcChasPowerSupplyDetailOperLineVoltage"
       REVISION "201402110000Z" -- 11 Feb 2014
       DESCRIPTION "Version 159: Changed thc chassis type from aVSP8284XSQ to
	                         a8284XSQ"
	   
       REVISION "201401100000Z" -- 10 Jan 2014
       DESCRIPTION "Version 158: Changed rcVSP6284XQ to rcVSP8284XSQ and add vsp8k8242XSQ
	                         card type"

       REVISION "201312110000Z" -- 11 December 2013
       DESCRIPTION "Version 157: Added rcSingleCpSystem"

       REVISION "201311150000Z" -- 15 November 2013
       DESCRIPTION "Version 156: Added cbHSFanTray(1085158144) for rcCardType"
	   
       REVISION "201311140000Z" -- 14 November 2013
       DESCRIPTION "Version 155: Added a4950GSXPWRPLUS"

       REVISION "201311130000Z" -- 13 November 2013
       DESCRIPTION "Version 154: Added rcVirtualIst"

       REVISION "201310100000Z" -- 10 October 2013
       DESCRIPTION "Version 153: Corrected syntax definitions."

       REVISION "201308090000Z" -- 09 Aug 2013
       DESCRIPTION "Version 152: Correct the VSP8000 to VSP6284XQ"
	   
       REVISION "201307100000Z" -- 10 July 2013
       DESCRIPTION "Version 151: Modified the values for rof4x40GBaseSFP and rof12x40GBaseSFP"
	   
       REVISION "201307030000Z" -- 03 July 2013
       DESCRIPTION "Version 150: Added rcIsid"
	   
       REVISION "201306190000Z" -- 19 June 2013
       DESCRIPTION "Version 149: Added rcVSP8000"

       REVISION "201306130000Z" -- 13 June 2013
       DESCRIPTION "Version 148: Added enumeration value - error(5) under
				 rcChasFanInfoOperSpeed"

       REVISION "201305090000Z" -- 09 May 2013
       DESCRIPTION "Version 147: Corrected the values of - 
	                         cbMidplaneSapphire (from 1090388737 to 1090396928),
				 cbFanTray (from 1085149953 to 1085154048) and
				 cbSF9610 (from 1075712769 to 1075716864).
				 These were created for a release 3.4), but
				 were later changed during the development 
				 phase of that release."

       REVISION "201304120000Z" -- 12 April 2013
       DESCRIPTION "Version 146: Remove BGP4-MIB from IMPORTS. Corrected
                                 syntax error in RcChasLedEntry."

       REVISION "201302200000Z" -- 20 February 2013
       DESCRIPTION "Version 145: Added rcLldp as {rcMgmt 210} and rcLldpEnable"

       REVISION "201301160000Z" -- 16 January 2013
       DESCRIPTION "Version 144: Changed the range of rcChasPowerSupplyId
	   			 from 1..6 to 1..8 since Sapphire chassis
				 has 8 power supplies."

       REVISION "201212190000Z" -- 19 December 2012
       DESCRIPTION "Version 143: Added rcVSP9010"

       REVISION "201212050000Z" -- 5 December 2012
       DESCRIPTION "Version 142: Added rcLacpNotificationObjects
	   		         and rcLacpMisconfigType"

       REVISION "201210260000Z" -- 26 October 2012
       DESCRIPTION "Version 141: Added rcWebLastHostAccessBlockedAddressType,
	   	                       rcWebLastHostAccessBlockedAddress and
				       deprecated rcWebLastHostAccessBlocked"
       REVISION "201210220000Z" -- 22 October 2012
       DESCRIPTION "Version 140: Added cbACPowerPlusSupply and cbFanTray rcCardType"

       REVISION "201210080000Z" -- 08 October 2012
       DESCRIPTION "Version 139: Added a9010 under rcChastype and 
	                         cbMidplaneSapphire and cbSF9610 under
				 rcCardType"

       REVISION "201209180000Z" -- 18 Sept 2012
       DESCRIPTION "Version 138: correct card type vsp4k4850GTSPWRPLUS"  
	   
       REVISION "201209170000Z" -- 17 Sept 2012
       DESCRIPTION "Version 137: Added rcSysDataPathFaultShutdownEnable"  

       REVISION "201208160000Z" -- 16 August 2012
       DESCRIPTION "Version 136: Added vsp4k4850GTS and vsp4k4850GTSPWR"  

       REVISION "201208130000Z" -- 13 August 2012
       DESCRIPTION "Version 135: Added rcChasLed and rcChasLedTable"  

       REVISION "201208110000Z" -- 11 August 2012
       DESCRIPTION "Version 134: Added enumeration a4850GTS(1232273458),
	                         a4850GTSPWR(1232277554) to rcChasType"  

       REVISION "201208020000Z" -- 02 August 2012
       DESCRIPTION "Version 133: Added rcChasRcBridgeFdbOldQueryFlagEnable"

       REVISION "201207310000Z" -- 31 July 2012
       DESCRIPTION "Version 132: Added rof48x1000SFP(1144152880),
	   			       rofLoadBoard(1144152832),
				       rof16x10GBaseSFP(1144218384),
				       rof48x10GBaseSFP(1144218416),
				       rof4x40GBaseSFP(1144283908),
				       rof12x40GBaseSFP(1144283916)"
				   
       REVISION "201207160000Z" -- 16 July 2012
       DESCRIPTION "Version 131: Added enum value of none(4) and changed
	   			 notApplicable to 5 (from 4) for 
				 rcChasPowerSupplyDetailDualAcInput"

       REVISION "201207130000Z" -- 13 July 2012
       DESCRIPTION "Version 130: Added rcChasPowerSupplyDetailDualAcInput
	   			 to the rcChasPowerSupplyDetailTable"

       REVISION "201207110000Z" -- 11 July 2012
       DESCRIPTION "Version 129: Added rcSlaMon"

       REVISION "201206270000Z" -- 27 June 2012
       DESCRIPTION "Version 128: Added rcSysSoftwareTable"

       REVISION "201204260000Z" -- 26 Apr 2012
       DESCRIPTION "Version 127: Changed the range of 
	   			 rcCliPasswordAccountUserName from 1..20 to 1..255
				 rcCliPasswordUserAccessLevel from 1..255 to 1..20"

       REVISION "201204050000Z" -- 05 Apr 2012
       DESCRIPTION "Version 126: Modified the names of the following objects -
	   			 rcCliUpperCase to rcCliPasswordUpperCase,
				 rcCliLowerCase to rcCliPasswordLowerCase,
				 rcCliNumbericCase to rcCliPasswordNumericCase,
				 rcCliSpecialCase to rcCliPasswordSpecialCase,
				 rcCliChangeInterval to rcCliPasswordChangeInterval,
				 rcCliPreNotificationInterval1 to rcCliPasswordPreNotificationInterval1,
				 rcCliPreNotificationInterval2 to rcCliPasswordPreNotificationInterval2,
				 rcCliPreNotificationInterval3 to rcCliPasswordPreNotificationInterval3,
				 rcCliPostNotificationInterval1 to rcCliPasswordPostNotificationInterval1,
				 rcCliPostNotificationInterval2 to rcCliPasswordPostNotificationInterval2,
				 rcCliPostNotificationInterval3 to rcCliPasswordPostNotificationInterval3,
				 Added tje following objects -
				 rcCliPasswordAccountIdleTime, 
				 rcCliPasswordAccountUserName,
				 rcCliPasswordUserAccessLevel,
				 rcCliPasswordPostExpiryLogins,
				 rcCliLoginAttemptErrorTrapEnable"

       REVISION "201203260000Z" -- 26 Mar 2012
       DESCRIPTION "Version 125: Added enumeration value of dualAc to
	   			 rcChasPowerSupplyDetailType mib object."

       REVISION "201203190000Z" -- 19 Mar 2012
       DESCRIPTION "Version 124: Added mib objects -
	   			 rcSyslogHostSecureForwardingEnable
	                         rcSyslogHostSecureForwardingSshProtect
				 and rcSyslogHostSecureForwardingTcpPort
				 under rcSyslogHostTbl."

       REVISION "201202130000Z" -- 13 Feb 2012
       DESCRIPTION "Version 123: Added TEXTUAL-CONVENTION LPortSet"

       REVISION "201201310000Z" -- 31 Jan 2012
       DESCRIPTION "Version 122: Added TEXTUAL-CONVENTION RcVlanIdOrNone"

       REVISION "201201090000Z" -- 09 Jan 2012
       DESCRIPTION "Version 121: Added rcSyslogHostAddressType and
	                         rcSyslogHostAddress  "

       REVISION "201111030000Z" -- 03 November 2011
       DESCRIPTION "Version 120: Added rcChasSecurityConsoleFlag"

       REVISION "201109130000Z" -- 13 September 2011
       DESCRIPTION "Version 119: Added rcSshGlobalDsaAuthKeyName and rcSshGlobalRsaAuthKeyName
                                 to rcSshGlobal;
                                 Modified description for rcSshcGlobalKeyFileName; 
                                 Deprecated rcSshcGlobalActiveSessions, rcSshcGlobalAuthenticationTimeout,
                                 rcSshcGlobalSftpServerAddress, rcSshcGlobalDsaAuth, rcSshcGlobalRsaAuth,
                                 rcSshcGlobalPassAuth.
                                 Modified range for rcSshcGlobalDsaKeySize, rcSshcGlobalRsaKeySize.
                                 Added enum values 5, 6 for rcSshcGlobalKeyAction.
                                 Added rcSshcGlobalRsaAuthenthication, rcSshcGlobalSftpServerPassword,
                                 rcSshcGlobalSftpServerInetAddressType, rcSshcGlobalSftpServerInetAddress 
                                 to rcSshcGlobal."

       REVISION "201109120000Z" -- 12 September 2011
       DESCRIPTION "Version 118: Added rcChasTakeIOCardOfflineEnable and
                                 rcChasAutoResetFabricEnable" 

       REVISION "201107270000Z" -- 27 July 2011
       DESCRIPTION "Version 117: Added rcVspTalk as {rcMgmt 208}" 

       REVISION "201106010000Z" -- 01 June 2011
       DESCRIPTION "Version 116: Added the correct range for rcWebHttpsPort"

       REVISION "201105260000Z" -- 26 May 2011
       DESCRIPTION "Version 115: Added rcIke, rcChasSystemDefault.
	                         Changed the upper limit of rcCliRWAPassword
				 and rcCliRWPassword. Added enum values
				 20 to 24 for rcCliPasswordChange. Added
				 rcCliRWAEnable, rcCliOperatorUserName, 
				 rcCliOperatorPassword, rcCliOperatorEnable,
				 rcCliSecurityUserName, rcCliSecurityPassword,
				 rcCliSecurityEnable, rcCliAuditorUserName,
				 rcCliAuditorPassword, rcCliAuditorEnable,
				 rcCliUpperCase, rcCliLowerCase, rcCliNumbericCase, 
				 rcCliSpecialCase, rcCliChangeInterval, 
				 rcCliPreNotificationInterval1, 
				 rcCliPreNotificationInterval2, 
				 rcCliPreNotificationInterval3, 
				 rcCliPostNotificationInterval1,
				 rcCliPostNotificationInterval2,
				 rcCliPostNotificationInterval3"

       REVISION "201103280000Z" -- 28 Mar 2011
       DESCRIPTION "Version 114: Support for SSHC.  Changed range for
                                 rcWebHttpsPort."

       REVISION "201102160000Z" -- 16 Feb 2011
       DESCRIPTION "Version 113: Added rcWlan."

       REVISION "201101100000Z" -- 10 Jan 2011
       DESCRIPTION "Version 112: Added rcLacpGlobalVlacpHoldTime."

       REVISION "201101030000Z" -- 03 Jan 2011
       DESCRIPTION "Version 111: Added rcSshGlobalRetries."

       REVISION "201011020000Z" -- 02 Nov 2010
       DESCRIPTION "Version 110: Corrected/Changed the rcVSP9000 to rcVSP9012."

       REVISION "201010150000Z" -- 15 Oct 2010
       DESCRIPTION "Version 109: Added rcSshcGlobal group."

       REVISION "201009130000Z" -- 13 Sep 2010
       DESCRIPTION "Version 108: Added rcSysTotalPower, rcSysRedundantPower, 
	                         rcSysAuthSuccessTrapEnable, rcSysUdpSrcByVirtualIpEnable, 
				 rcChasFanZoneTable, rcChasFanInfoTable, 
				 rcChasPowerSupplyDetailOutputWatts, rcCardOxateCpld, 
				 rcCardOxideFpga, rcCardCatskillFpga, rcCardQE, rcCardK2Fpga, 
				 rcCardIoDateDC, rcCardIoDateBB, rcCardIoPimCpld, rcCardLed0Cpld, 
				 rcCardLed1Cpld, rcCardZagrosFpga, rcCardRsp, rcCardBcmMac, 
				 rcCardPhosphideFpga, rcCardSulfideFpga, rcCardFluorateCpld, 
				 rcCardBme, rcWebSecureOnly, rcUserSetTimeTimezone.
				 Added a new type a9012 under rcChasType.
				 Changed the range for rcChasPowerSupplyId and 
				 rcChasPowerSupplyDetailId from (1..3) to (1..6).
				 Changed the range for rcCardIndex from (1..10) to (1..26).
				 Added new types (for CB - 1090388736, 1084097280, 1085145856, 
				 1085149952, 1091437312, 1075708672, 1075712768, 1073873665, 
				 1075970864, 1075974960, 1077044016, 1077109528, 1077109552) 
				 under rcCardType."

       REVISION "201008250000Z" -- 25 Aug 2010
       DESCRIPTION "Version 107: Merged latest versions."

       REVISION "201008170000Z" -- 17 August 2010
       DESCRIPTION "Version 106: Added rcERS8603r, rcA8803r, rcA8806, rcA8810,
                                 rcA8810co.  Corrected rcVrrp3 to rcVrrpv3"

       REVISION "201002220000Z" -- 22 Feb 2010
       DESCRIPTION "Version 105: Added rcERS8603r, rcA8803r, rcA8806,
                                       rcA8810, rcA8810co."

       REVISION "200912140000Z" -- 14 December 2009
       DESCRIPTION "Version 104: Assigning the SysObjectID for VSP9000 to 201"

       REVISION "200910260000Z" -- 26 October 2009
       DESCRIPTION "Version 103: Added option webPassWdRwa to mib object
                                 rcCliPasswordChange"

       REVISION "200910130000Z" -- 13 October 2009
       DESCRIPTION "Version 102: Added option adminDisable and notApplicable
                                 to KhiStatusValue"

       REVISION "200909150000Z" -- 15 September 2009
       DESCRIPTION "Version 101: Added KhiStatusValue in textual convention.
                                 Imported TimeInterval,
                                          InetAutonomousSystemNumber
                                 Added rcKhi and rcVrrp3."

       REVISION "201002220000Z" -- 22 Feb 2010
       DESCRIPTION "Version 100: Added rcERS8603r, rcA8803r, rcA8806,
                                       rcA8810, rcA8810co."

       REVISION "200905110000Z" -- 11 May 2009
       DESCRIPTION "Version 99: Added rcLacpGlobalSystemMac, rcLacpKeyTable."

       REVISION "200903250000Z" -- 25 March 2009
       DESCRIPTION "Version 95: Added rcSystem 104 to 115. "

       REVISION "200902270000Z" -- 27 Feb 2009
       DESCRIPTION "Version 94: rcSysCopHighCpuUtilThreshold default value
                                changed to 100"

       REVISION "200902260000Z" -- 26 Feb 2009
       DESCRIPTION "Version 93: Added rcLinkOam, rcAccessMstp and rcDhu"

       REVISION "200809230000Z" -- 23 September 2008
       DESCRIPTION "Version 92: Added rcSysSingleMgmtIpAddr,
                                      rcSysCopHighCpuUtilThreshold,
                                      rcSysCopHighCpuUtilLogTime,
                                      rcChasSwitchFabricRedundancy. 
                                Modified rcSysAction,
                                         rcSysActionRwa,
                                         RcChasPowerSupplyDetailEntry "

       REVISION "200809110000Z" -- 11 September 2008
       DESCRIPTION "Version 91: Added rcOlc"

       REVISION "200807140000Z" -- 14 July 2008
       DESCRIPTION "Version 90: Added rcChasEsmHashIndex"

       REVISION "200807020000Z" -- 02 July 2008
       DESCRIPTION "Version 89: Change range of rcCardPartNumber from (0..6)
                                to (0..16) due to it does not match with both
                                ERS8300 and ERS8600."
       
       REVISION "200805120000Z" -- 12 May 2008
       DESCRIPTION "Version 88: Fixed smilint errors."

       REVISION "200805080000Z" -- 08 May 2008
       DESCRIPTION "Version 87: Fixed compile error."

       REVISION "200805071000Z" -- 07 May 2008
       DESCRIPTION "Version 86: Added minus48V as an enum value to
                                rcChasPowerSupplyDetailInputLineVoltage
				                and rcChasPowerSupplyDetailOperLineVoltage."

       REVISION "200805070000Z" -- 07 May 2008
       DESCRIPTION "Version 85: Added rcMmrp as rcMgmt 44"	
	
       REVISION "200805051200Z" -- 05 May 2008
       DESCRIPTION "Version 84: Added rcCobaltBlue"

       REVISION "200805050000Z" -- 05 May 2008
       DESCRIPTION "Version 83: Added New TC 'RcLongDisplayString'."

       REVISION "200803140000Z" -- 14 March 2008
       DESCRIPTION "Version 82: Modified rcChasPowerManagementEnable"

       REVISION "200803130000Z" -- 13 March 2008
       DESCRIPTION "Version 81: Changed rcVirtualRouterMIB to rcVrf"

       REVISION "200803040000Z" -- 4 March 2008
       DESCRIPTION "Version 80: Added rcBfd."

       REVISION "200802190000Z" -- 19 February 2008
       DESCRIPTION "Version 79: Added
                                rcChasPowerSupplyDetailInputLineVoltage and
                                rcChasPowerSupplyDetailOperLineVoltage."

       REVISION "200802140000Z" -- 14 Feb 2008
       DESCRIPTION "Version 78: Added rcChasPowerManagementOriginalEnable,
				rcChasPowerManagementFanCheck and 
				rcChasPowerManagementFanCheckOriginalState. 
				Also modified the Description of rcChasPowerManagementEnable"                            
      
       REVISION "200802110000Z" -- 11 Feb 2008
       DESCRIPTION "Version 77: Added a8003r(280891651) to rcChasType,
	                              rapidCity 55"

       REVISION "200801250000Z" -- 25 Jan 2008
       DESCRIPTION "Version 76: Added new dc power supply type dc8005(0x10901000)"

       REVISION "200801220000Z" -- 22 Jan 2008
       DESCRIPTION "Version 75: Changed the range of rcChasCircuitlessIpId."

       REVISION "200801040000Z" -- 4 Jan 2008
       DESCRIPTION "Version 74: Added the rcMsdp as rcMgmt 80."

       REVISION "200712240000Z" -- 24 Dec 2007
       DESCRIPTION "Version 73: Updated rcChassis, rcVlacpGlobal objects."

       REVISION "200710190000Z" -- 19 Oct 2007
       DESCRIPTION "Version 72: Added rapidCity 54,
                                      a8011co(1623064843) to rcChasType,
                                      rcCoreDump, rcCoreDumpGlobal."

       REVISION "200710180000Z" -- 18 Oct 2007
       DESCRIPTION "Version 71: Changed syntax of rcChasCircuitlessIpId for 
                                SMIv2 compliance."

       REVISION "200710150000Z" -- 15 Oct 2007
       DESCRIPTION "Version 70: Changed rcSysLicenseRemainingDays to 
                                rcSysLicenseTrialDaysLeft."

       REVISION "200710040000Z" -- 04 Oct 2007
       DESCRIPTION "Version 69: Added rcSysLicenseRemainingDays to rcSystem"

       REVISION "200709200000Z" -- 20 Sep 2007
       DESCRIPTION "Version 68: Added rcChasForceTopologyIpFlagEnable,
                    rcChasCircuitlessIpId and modified rcChasPowerManagementEnable"

       REVISION "200709170000Z" -- 17 Sep 2007
       DESCRIPTION "Version 67: Added rcVlacpGlobal."

       REVISION "200708170000Z" -- 17 Aug 2007
       DESCRIPTION "Version 66: Modify rcChasPowerManagementEnable."

       REVISION "200706150000Z" -- 15 June 2007
       DESCRIPTION "Version 65: Added rcChasPowerManagementEnable."

       REVISION "200706060000Z" -- 06 June 2007
       DESCRIPTION "Version 64: Added rcSyslogGlobalHeader"

       REVISION "200705300000Z" -- 30 May 2007
       DESCRIPTION "Version 63: Added rcPlsb"

       REVISION "200704200000Z" -- 20 April 2007
       DESCRIPTION "Version 62: Added rcCsuGlobal and rcCsuInfoTable"
                                
       REVISION "200704170000Z" -- 16 April 2007
       DESCRIPTION "Version 61: Modified rcSysActionRwa
                                Added default value for rcSysAutoRecoverDelay
				Added rcSysExtendedPingBypass group"

       REVISION "200703150000Z" -- 15 March 2007
       DESCRIPTION "Version 60: added rcCsu"

       REVISION "200703120000Z" -- 12 March 2007
       DESCRIPTION "Version 59: Updated rcSysActionL2"

       REVISION "200703100000Z" -- 10 March 2007
       DESCRIPTION "Version 58: Updated rcSysActionL1"

       REVISION "200703060000Z" -- 06 March 2007
       DESCRIPTION "Version 57: Added rcSysConfigMode, rcChasNewMulticastResourceReservation, 
		rcChasMulticastResourceReservation, rcChasNewMaxVlanResourceReservation,
		rcChasMaxVlanResourceReservation, rcChasMgidUsageVlanCurrent,
		rcChasMgidUsageVlanRemaining, rcChasMgidUsageMulticastCurrent,
		rcChasMgidUsageMulticastRemaining"

       REVISION "200701030000Z" -- 03 Jan 2007
       DESCRIPTION "Version 56: Added rcVirtualRouterMIB"

       REVISION "200701020000Z" -- 02 Jan 2007
       DESCRIPTION "Version 55: Added rcRing"

       REVISION "200612070000Z" -- 07 Dec 2006
       DESCRIPTION "Version 54: Updated rcMpls; Added rcVrrp, rcPim, rcIpMRoute"

       REVISION "200608110000Z" -- 11 August 2006
       DESCRIPTION "Verion 53: Added rcMpls"
       
       REVISION "200607050000Z" -- 07 July 2006
       DESCRIPTION "Verion 52: Added rcChassis 42 and 43 for CR Q01384676"

       REVISION "200606210000Z" -- 21 June 2006
       DESCRIPTION "Verion 51: Added rcPwe3, rcPlugOptMod and rc8021ah"

       REVISION "200603240000Z" -- 24 March 2006
       DESCRIPTION "Verion 50: Updated rcSysAccessPolicyNetInetAddrType"

       REVISION "200602100000Z" -- 10 February 2006
       DESCRIPTION "Verion 49: Added objects rcLacpGlobal 9-13"

       REVISION "200602030000Z" -- 03 February 2006
       DESCRIPTION "Verion 48: Added rcCfm for OE Connectivity Fault Management feature"
	
       REVISION "200601040000Z" -- 04 January 2006
       DESCRIPTION "Verion 47: Added CfmNameString type for OE Connectivity Fault Management feature"
	
       REVISION "200510210000Z" -- 21 October 2005
       DESCRIPTION "Verion 46: Added new mibs rcFlowClassifier for 1600"
	
       REVISION "200509300000Z" -- 30 Sep 2005
       DESCRIPTION "Version 45: Modified rcSysDnsServerListTable, sorted objects in rcChassis, & added rcChasSystemMonitorEnable"

       REVISION "200509200000Z" -- 20 Sep 2005
       DESCRIPTION "Version 44: Added Ipv6 attributes to various tables"

       REVISION "200509090000Z" -- 09 Sep 2005
       DESCRIPTION "Version 43: Added rcSysVirtualIpv6PrefixLength & rcSysVirtualIpv6Addr"

       REVISION "200508290000Z" -- 29 Aug 2005
       DESCRIPTION "Version 42: Added rcIsis & rcSlpp"

       REVISION "200507270000Z" -- 27 July 2005
       DESCRIPTION "Version 41. Increased range for rcCardIndex"

       REVISION "200507190000Z" -- 19 Jul 2005
       DESCRIPTION "Version 40. Added rcSysAccPolSnmpGrpTable.Included snmp-v3 under 
       access policy service, removed the default value"

       REVISION "200506020000Z" -- 02 Jun 2005
       DESCRIPTION "Version 39. Added rcChasMcastCheckPktEnable."

       REVISION "200505060000Z" -- 06 May 2005
       DESCRIPTION "Version 39. Added rcSysFrcMsgControlTable."

       REVISION "200504270000Z" -- 27 Apr 2005
       DESCRIPTION "Version 38. Allow 0 length rsa and dsa key sizes."

       REVISION "200504210000Z" -- 21 Apr 2005
       DESCRIPTION "Version 37. Fixed typos, added rcIpfix."

       REVISION "200504140000Z" -- 14 Apr 2005
       DESCRIPTION "Version 36. Modified rcSysAccessPolicyService &
                                rcSyslogHostSeverity mib objects."

       REVISION "200503210000Z" -- 21 Mar 2005
       DESCRIPTION "Version 35: added rcLacpGlobalVlacpMulticastMACAddress."

       REVISION "200502220000Z" -- 22 Feb 2005
       DESCRIPTION "Version 34: Changed PortSet definition"

       REVISION "200502181200Z" -- 18 Feb 2005
       DESCRIPTION "Version 33: Added support for Tacacs"

       REVISION "200502171200Z" -- 17 Feb 2005
       DESCRIPTION "Version 32: Updated teritory to tertiary"

       REVISION "200502150000Z" -- 15 Feb 2005
       DESCRIPTION "Version 31: Added rcEsu1800dc"

       REVISION "200502110000Z" -- 11 Feb 2005
       DESCRIPTION "Version 30: Added rcSystem 92 & 93"

       REVISION "200502040000Z" -- 04 Feb 2005
       DESCRIPTION "Version 29: Changed range of rcSysVersion, rcCardSerialNumber,
                                rcChasPowerSupplyDetailSerialNumber,
                                rcChasPowerSupplyDetailHardwareRevision,
                                rcChasPowerSupplyDetailPartNumber,
                                rcCardSerialNumber"

       REVISION "200501160000Z" -- 16 January 2005
       DESCRIPTION "Version 28: Added rcSysPowerUsage and rcSysPowerAvailable"

       REVISION "200412210000Z" -- 21 December 2004
       DESCRIPTION "Version 27: Deprecated rcSysAction. Added 
                                rcSysExtCplimitSysOctapidCongested,
                                rcSysExtCplimitPortsMonitored,
                                rcSysExtCplimitPortsShutDown,
                                rcSysActionL1, rcSysActionL2,
                                rcSysActionL3, rcSysActionRwa "

       REVISION "200411230000Z" -- 23 November 2004
       DESCRIPTION "Version 26: Added rcEsu1850 and rcEsu1850dc for ESU device"

       REVISION "200411110000Z" -- 11 November 2004
       DESCRIPTION "Version 25: Cleaned up REVISIONs and fixed typo."

       REVISION "200411040000Z" -- 04 November 2004
       DESCRIPTION "Version 24: Added rcSysExtCplimitEnable,rcSysExtCplimitMinCongTime,
                                rcSysExtCplimitMaxPorts, rcSysExtCplimitPortCongTime,
                                rcSysExtCplimitTrapLevel."

       REVISION "200409300000Z" -- 30 September 2004
       DESCRIPTION "Version 22: Fixed type mismatch for mib
                                rcSysDnsServerListRequestCount/SuccessCount"

       REVISION "200409280000Z" -- 28 September 2004
       DESCRIPTION "Version 21: Update enum value for mib rcSysDnsServerListType,
                                update syntax type for RequestCount, SuccessCount,
                                change rcRepeaterTable OID and add new mib
                                rcChasNewGlobalFilterOrderingEnable."

       REVISION "200409230000Z" -- 23 September 2004
       DESCRIPTION "Version 20: Add range for rcAgentId."

       REVISION "200409210000Z" -- 21 September 2004
       DESCRIPTION "Version 19: Remove range for rcAgentId."  

       REVISION "200409130001Z" -- 13 September 2004
       DESCRIPTION "Version 18: Added rcCliRWEnable, rcCliRWL1Enable, rcCliRWL2Enable,
                                rcCliRWL3Enable, rcCliROEnable."  

       REVISION "200409130000Z" -- 13 September 2004
       DESCRIPTION "Version 17: Added rcSysAutoRecoverDelay, rcSysMacFlapLimitTime,
                                rcSysMacFlapLimitCount"  

       REVISION "200408310000Z" -- 31 August 2004
       DESCRIPTION "Version 16: Change rcVlacpPeerMacAddressMltIds to
                                rcVlacpPeerMacAddressMltId with SYNTAX INTEGER and
                                rcVlacpPeerMacAddressPort with SYNTAX InterfaceIndex"  

       REVISION "200407070000Z" -- 07 July 2004
       DESCRIPTION "Version 15: Added rcVlacpPeerMacAddressTable"  

       REVISION "200407060000Z" -- 06 July 2004
       DESCRIPTION "Version 14:  Added Poe card type poe1400WPS(0x109e3100)"

       REVISION "200406240000Z" -- 24 June 2004
       DESCRIPTION "Version 13:  Added rcSysSpanningTreeOperMode and
                                 rcSysSpanningTreeAdminMode"

       REVISION "200406110000Z" -- 11 June 2004
       DESCRIPTION "Version 12:  Added rcChasRspMode, rcChasRspOperMode,
                                 and rcChasRspModeError objects"

       ::= { enterprises 2272 }

-- 
-- Textual Conventions
--

EnableValue ::= TEXTUAL-CONVENTION
    STATUS      current
    DESCRIPTION "Enable/Disable value."
    SYNTAX      INTEGER { enable(1), disable(2) }

PortSet         ::= TEXTUAL-CONVENTION
    STATUS      current
    DESCRIPTION
        "The string is 88 octets long, for a total of 704 bits. Each bit
         corresponds to a port, as represented by its ifIndex value . When a
         bit has the value one(1), the corresponding port is a member of the
         set. When a bit has the value zero(0), the corresponding port is not
         a member of the set. The encoding is such that the most significant
         bit of octet #1 corresponds to ifIndex 0, while the least significant
         bit of octet #88 corresponds to ifIndex 703.  In order to accommodate
         future uses of this the string has a max size of 255 bytes."
    SYNTAX      OCTET STRING (SIZE (0..255))

IdList ::= TEXTUAL-CONVENTION
    STATUS      current
    DESCRIPTION ""
    SYNTAX      OCTET STRING (SIZE(0..8192))

CfmNameString ::= TEXTUAL-CONVENTION
        STATUS current
        DESCRIPTION
            "CFM Name String"
        SYNTAX OCTET STRING (SIZE(0..32))

RcLongDisplayString ::= TEXTUAL-CONVENTION
   STATUS       current
   DESCRIPTION  "The semantics are identical to the standard DisplayString
                in RFC1213 and RFC2579, except for the longer length that
                is allowed with this TC. "
   SYNTAX       OCTET STRING (SIZE(0..65535))

KhiStatusValue ::= TEXTUAL-CONVENTION
   STATUS       current
   DESCRIPTION  "Key Health Indication status defintion
                     green(1): normal status.
                     yellow(2): Alert.
                     red(3): critical state.
                     adminDisable(4): administately disable.
                     notApplicable(5): either not config or not applicable"
   SYNTAX       INTEGER {
                            green(1),
                            yellow(2),
                            red(3),
                            adminDisable(4),
                            notApplicable(5)
                        }

RcVlanIdOrNone ::= TEXTUAL-CONVENTION
    STATUS current
    DESCRIPTION
            "Range of VLAN IDs supported for application"
    SYNTAX INTEGER (1..4094)

LPortSet         ::= TEXTUAL-CONVENTION
    STATUS      current
    DESCRIPTION
        "The string is 256 octets long, for a total of 2048 bits. Each bit
         corresponds to a logical port, as represented by its ifIndex value . 
         When a bit has the value one(1), the corresponding port is a member 
         of the set. When a bit has the value zero(0), the corresponding 
         logical port is not a member of the set. The encoding is such that 
         the most significant bit of octet #1 corresponds to ifIndex 704, 
         while the least significant bit of octet #256 corresponds to 
         ifIndex 2752. "
    SYNTAX      OCTET STRING (SIZE (0..256))

--
-- Enterprise specific MIB groups
--
rcMgmt 			OBJECT IDENTIFIER ::= { rapidCity 1 }
rcA1100			OBJECT IDENTIFIER ::= { rapidCity 2 }
rcA1250    		OBJECT IDENTIFIER ::= { rapidCity 6 }
rcA1150    		OBJECT IDENTIFIER ::= { rapidCity 7 }
rcA1200    		OBJECT IDENTIFIER ::= { rapidCity 8 }
rcA1050    		OBJECT IDENTIFIER ::= { rapidCity 9 }
rcA740                  OBJECT IDENTIFIER ::= { rapidCity 20 }
rcA750                  OBJECT IDENTIFIER ::= { rapidCity 21 }
rcA790                  OBJECT IDENTIFIER ::= { rapidCity 22 }
rcA750S                 OBJECT IDENTIFIER ::= { rapidCity 23 }
rcA8003    		OBJECT IDENTIFIER ::= { rapidCity 280887555 }
rcA8006    		OBJECT IDENTIFIER ::= { rapidCity 280887558 }
rcA8010    		OBJECT IDENTIFIER ::= { rapidCity 280887562 }
rcA8010co               OBJECT IDENTIFIER ::= { rapidCity 1623064842 }
rcA8610    		OBJECT IDENTIFIER ::= { rapidCity 30 }
rcA8606    		OBJECT IDENTIFIER ::= { rapidCity 31 }
rcA8110    		OBJECT IDENTIFIER ::= { rapidCity 32 }
rcA8106    		OBJECT IDENTIFIER ::= { rapidCity 33 }
rcA8603    		OBJECT IDENTIFIER ::= { rapidCity 34 }
rcA8103    		OBJECT IDENTIFIER ::= { rapidCity 35 }
rcA8110co               OBJECT IDENTIFIER ::= { rapidCity 36 }
rcA8610co               OBJECT IDENTIFIER ::= { rapidCity 37 }
-- This is a place holder for OM 2.0 chassises
-- NOTE that { rapidCity 40 } is also used for the rcBayStack branch,
-- and so we must be sure that nothing ever gets defined under rcAom8003
-- in order to avoid any conflicts.
--rcAom8010                 OBJECT IDENTIFIER ::= { rapidCity 38 }
--rcAom8010co               OBJECT IDENTIFIER ::= { rapidCity 39 }
rcBayStack                   OBJECT IDENTIFIER ::= { rapidCity 40 }
--rcAom8006                 OBJECT IDENTIFIER ::= { rapidCity 41 }
rcA1424                 OBJECT IDENTIFIER ::= { rapidCity 42 }
rcA1648                 OBJECT IDENTIFIER ::= { rapidCity 43 }
rcA1612                 OBJECT IDENTIFIER ::= { rapidCity 44 }
rcA1624                 OBJECT IDENTIFIER ::= { rapidCity 45 }
rcRBS2402               OBJECT IDENTIFIER ::= { rapidCity 46 }
rcAtr8310               OBJECT IDENTIFIER ::= { rapidCity 47 }
rcAtr8306               OBJECT IDENTIFIER ::= { rapidCity 48 }
rcAtr8010               OBJECT IDENTIFIER ::= { rapidCity 49 }
rcAtr8006               OBJECT IDENTIFIER ::= { rapidCity 50 }
rcEsu1850               OBJECT IDENTIFIER ::= { rapidCity 51 }   
rcEsu1850dc             OBJECT IDENTIFIER ::= { rapidCity 52 }   
rcEsu1800dc             OBJECT IDENTIFIER ::= { rapidCity 53 } 
rcA8611co               OBJECT IDENTIFIER ::= { rapidCity 54 }  
rcA8603r 		OBJECT IDENTIFIER ::= { rapidCity 55 }
rcERS8603r              OBJECT IDENTIFIER ::= { rapidCity 56 }
rcA8803r                OBJECT IDENTIFIER ::= { rapidCity 57 }
rcA8806                 OBJECT IDENTIFIER ::= { rapidCity 58 }
rcA8810                 OBJECT IDENTIFIER ::= { rapidCity 59 }
rcA8810co               OBJECT IDENTIFIER ::= { rapidCity 60 }

-- From rapidCity 100 to rapidCity 200 is reserved for OM chassises
rcVSP9012               OBJECT IDENTIFIER ::= { rapidCity 201 }
rcVSP4850GTS            OBJECT IDENTIFIER ::= { rapidCity 202 }
rcVSP4850GTSPWRPLUS     OBJECT IDENTIFIER ::= { rapidCity 203 }
rcVSP9010               OBJECT IDENTIFIER ::= { rapidCity 204 }
rcVSP8284XSQ            OBJECT IDENTIFIER ::= { rapidCity 205 }
rcVSP4450GSXPWRPLUS     OBJECT IDENTIFIER ::= { rapidCity 206 }
rcVSP4450GTXHTPWRPLUS   OBJECT IDENTIFIER ::= { rapidCity 207 }
rcVSP8404               OBJECT IDENTIFIER ::= { rapidCity 208 }
rcVSP7254XSQ		OBJECT IDENTIFIER ::= { rapidCity 209 }
rcVSP7254XTQ		OBJECT IDENTIFIER ::= { rapidCity 210 }
rcVSP4450GSX            OBJECT IDENTIFIER ::= { rapidCity 211 }
rcVSP8608               OBJECT IDENTIFIER ::= { rapidCity 212 }
-- APLS device start
rcDSG8032               OBJECT IDENTIFIER ::= { rapidCity 213 }
rcDSG6248CFP            OBJECT IDENTIFIER ::= { rapidCity 214 }
rcDSG7648               OBJECT IDENTIFIER ::= { rapidCity 215 }
rcDSG7648C              OBJECT IDENTIFIER ::= { rapidCity 216 }
rcDSG7480               OBJECT IDENTIFIER ::= { rapidCity 217 }
rcDSG6248               OBJECT IDENTIFIER ::= { rapidCity 218 }
rcDSG6248P              OBJECT IDENTIFIER ::= { rapidCity 219 }
rcVSP8404C              OBJECT IDENTIFIER ::= { rapidCity 220 }
rcDSG9032               OBJECT IDENTIFIER ::= { rapidCity 221 }
rcDSG8064               OBJECT IDENTIFIER ::= { rapidCity 222 }
rcVSP5030GSXuPWR        OBJECT IDENTIFIER ::= { rapidCity 223 }
rcVSP5054GSXuPWR        OBJECT IDENTIFIER ::= { rapidCity 224 }
-- No longer use Rappid city System OID. 
-- Need to define and use Extreme sys OID
--
-- MIB groups.  Note that the ones that are commented out are now defined in
-- separate MIB files.  These are kept as placeholders here.
--
rcSystem  		OBJECT IDENTIFIER ::= { rcMgmt 1 }
rcTftp 	  		OBJECT IDENTIFIER ::= { rcMgmt 2 }
rcVlan 	  		OBJECT IDENTIFIER ::= { rcMgmt 3 }
rcChassis 		OBJECT IDENTIFIER ::= { rcMgmt 4 }
rcMirror		OBJECT IDENTIFIER ::= { rcMgmt 5 }
rcDipSwitch		OBJECT IDENTIFIER ::= { rcMgmt 6 }
rcTblSize		OBJECT IDENTIFIER ::= { rcMgmt 7 }
rcIp			OBJECT IDENTIFIER ::= { rcMgmt 8 }
rcArp			OBJECT IDENTIFIER ::= { rcMgmt 9 }
rcRip			OBJECT IDENTIFIER ::= { rcMgmt 10 }
rcTest			OBJECT IDENTIFIER ::= { rcMgmt 11 }
rcStat			OBJECT IDENTIFIER ::= { rcMgmt 12 }
rcStg			OBJECT IDENTIFIER ::= { rcMgmt 13 }
rcBridge		OBJECT IDENTIFIER ::= { rcMgmt 14 }
rcBoot			OBJECT IDENTIFIER ::= { rcMgmt 15 }
rcDevice		OBJECT IDENTIFIER ::= { rcMgmt 16 }
rcMlt			OBJECT IDENTIFIER ::= { rcMgmt 17 }
rcWeb			OBJECT IDENTIFIER ::= { rcMgmt 18 }
rcCli			OBJECT IDENTIFIER ::= { rcMgmt 19 }
rcError			OBJECT IDENTIFIER ::= { rcMgmt 20 }
rcTraps			OBJECT IDENTIFIER ::= { rcMgmt 21 }
rcSyslog		OBJECT IDENTIFIER ::= { rcMgmt 22 }
rcDiag          	OBJECT IDENTIFIER ::= { rcMgmt 23 }
rcIpx 			OBJECT IDENTIFIER ::= { rcMgmt 24 }
rcPos                   OBJECT IDENTIFIER ::= { rcMgmt 26 }
rcLinkFlapDetect        OBJECT IDENTIFIER ::= { rcMgmt 27 }
rcV1Traps               OBJECT IDENTIFIER ::= { rcMgmt 28 }
rcRadius                OBJECT IDENTIFIER ::= { rcMgmt 29 }
rcIgmp                  OBJECT IDENTIFIER ::= { rcMgmt 30 }
rcUserSetTime           OBJECT IDENTIFIER ::= { rcMgmt 31 }
rcL2Redundancy          OBJECT IDENTIFIER ::= { rcMgmt 32 }
rcNtp        		OBJECT IDENTIFIER ::= { rcMgmt 33 }
rcSsh        		OBJECT IDENTIFIER ::= { rcMgmt 34 }
rcSvlan        		OBJECT IDENTIFIER ::= { rcMgmt 35 }
rcOpm                   OBJECT IDENTIFIER ::= { rcMgmt 36 }
rcVpn                   OBJECT IDENTIFIER ::= { rcMgmt 37 }
rcOeAdm                 OBJECT IDENTIFIER ::= { rcMgmt 38 }
rcTlsVpn                OBJECT IDENTIFIER ::= { rcMgmt 39 }
rcTls                   OBJECT IDENTIFIER ::= { rcMgmt 40 }
rcCos                   OBJECT IDENTIFIER ::= { rcMgmt 41 }
rcBanRing               OBJECT IDENTIFIER ::= { rcMgmt 42 }
rcRing                  OBJECT IDENTIFIER ::= { rcMgmt 43 }
rcMmrp                  OBJECT IDENTIFIER ::= { rcMgmt 44 }
rcTengEnet      	OBJECT IDENTIFIER ::= { rcMgmt 50 }
rcRec                   OBJECT IDENTIFIER ::= { rcMgmt 51 }
rcTdc                   OBJECT IDENTIFIER ::= { rcMgmt 52 }
rcLacp                  OBJECT IDENTIFIER ::= { rcMgmt 53 }
rcQos                   OBJECT IDENTIFIER ::= { rcMgmt 54 }
rcFilter                OBJECT IDENTIFIER ::= { rcMgmt 55 }
rcLicense               OBJECT IDENTIFIER ::= { rcMgmt 56 }
rcEap                   OBJECT IDENTIFIER ::= { rcMgmt 57 }
rcMcast                 OBJECT IDENTIFIER ::= { rcMgmt 58 }
rcOspf                  OBJECT IDENTIFIER ::= { rcMgmt 59 }
rcFdb                   OBJECT IDENTIFIER ::= { rcMgmt 60 }
rcIgap                  OBJECT IDENTIFIER ::= { rcMgmt 61 }
rcIpv6                  OBJECT IDENTIFIER ::= { rcMgmt 62 }
rcIsis	                OBJECT IDENTIFIER ::= { rcMgmt 63 }
rcSlpp	                OBJECT IDENTIFIER ::= { rcMgmt 64 }
rcTacacs                OBJECT IDENTIFIER ::= { rcMgmt 65 }
rcIpfix                 OBJECT IDENTIFIER ::= { rcMgmt 66 }
rcOspfv3	        OBJECT IDENTIFIER ::= { rcMgmt 67 }
rcFlowClassifier        OBJECT IDENTIFIER ::= { rcMgmt 68 }
rcCfm                   OBJECT IDENTIFIER ::= { rcMgmt 69 }
rcPwe3                  OBJECT IDENTIFIER ::= { rcMgmt 70 }
rcPlugOptMod            OBJECT IDENTIFIER ::= { rcMgmt 71 }
rc8021ah                OBJECT IDENTIFIER ::= { rcMgmt 72 }
rcVrrp                  OBJECT IDENTIFIER ::= { rcMgmt 73 }
rcMpls                  OBJECT IDENTIFIER ::= { rcMgmt 74 }
rcPim                   OBJECT IDENTIFIER ::= { rcMgmt 75 }
rcIpMRoute              OBJECT IDENTIFIER ::= { rcMgmt 76 }
rcCsu                   OBJECT IDENTIFIER ::= { rcMgmt 77 }
rcPlsb                  OBJECT IDENTIFIER ::= { rcMgmt 78 }
rcCoreDump              OBJECT IDENTIFIER ::= { rcMgmt 79 }
rcMsdp                  OBJECT IDENTIFIER ::= { rcMgmt 80 }
rcBfd                   OBJECT IDENTIFIER ::= { rcMgmt 81 }
rcLinkOam               OBJECT IDENTIFIER ::= { rcMgmt 82 }
rcAccessMstp            OBJECT IDENTIFIER ::= { rcMgmt 83 }
rcDhu                   OBJECT IDENTIFIER ::= { rcMgmt 84 }
rcKhi                   OBJECT IDENTIFIER ::= { rcMgmt 85 }
rcIke                   OBJECT IDENTIFIER ::= { rcMgmt 86 }
rcIsid                  OBJECT IDENTIFIER ::= { rcMgmt 87 }
rcMACSec                OBJECT IDENTIFIER ::= { rcMgmt 88 }
rc2k                    OBJECT IDENTIFIER ::= { rcMgmt 100 }
rcVossSystem            OBJECT IDENTIFIER ::= { rcMgmt 101 }
rcCliSystem             OBJECT IDENTIFIER ::= { rcMgmt 102 }
rcSmtp                  OBJECT IDENTIFIER ::= { rcMgmt 103 }
rcOm8k                  OBJECT IDENTIFIER ::= { rcMgmt 200 }
cobra                   OBJECT IDENTIFIER ::= { rcMgmt 201 }
rcPowerRanger           OBJECT IDENTIFIER ::= { rcMgmt 202 }
rcVrf                   OBJECT IDENTIFIER ::= { rcMgmt 203 }
rcCobaltBlue            OBJECT IDENTIFIER ::= { rcMgmt 204 }
rcOlc                   OBJECT IDENTIFIER ::= { rcMgmt 205 }
rcVrrpv3                OBJECT IDENTIFIER ::= { rcMgmt 206 }
rcWlan                  OBJECT IDENTIFIER ::= { rcMgmt 207 }
rcVspTalk               OBJECT IDENTIFIER ::= { rcMgmt 208 }
rcSlaMon                OBJECT IDENTIFIER ::= { rcMgmt 209 }
rcLldp                  OBJECT IDENTIFIER ::= { rcMgmt 210 }
rcVirtualIst            OBJECT IDENTIFIER ::= { rcMgmt 211 }
rcSingleCpSystem        OBJECT IDENTIFIER ::= { rcMgmt 212 }
rcIpsec                 OBJECT IDENTIFIER ::= { rcMgmt 213 }
rcASG                   OBJECT IDENTIFIER ::= { rcMgmt 214 }
rcMld                   OBJECT IDENTIFIER ::= { rcMgmt 215 }
rcMRouteIpv6            OBJECT IDENTIFIER ::= { rcMgmt 216 }
rcPimIpv6               OBJECT IDENTIFIER ::= { rcMgmt 217 }
rcVxlan                 OBJECT IDENTIFIER ::= { rcMgmt 218 }
rcDvr                   OBJECT IDENTIFIER ::= { rcMgmt 219 }
rcLldpExt               OBJECT IDENTIFIER ::= { rcMgmt 220 }
rcSflow                 OBJECT IDENTIFIER ::= { rcMgmt 221 }
rcDigitalCert           OBJECT IDENTIFIER ::= { rcMgmt 222 }
rcNls                   OBJECT IDENTIFIER ::= { rcMgmt 223 }
rcCarrier               OBJECT IDENTIFIER ::= { rcMgmt 224 }
rcOvsdb                 OBJECT IDENTIFIER ::= { rcMgmt 225 }
rcAppTelemetry          OBJECT IDENTIFIER ::= { rcMgmt 226 }
rcRestConf              OBJECT IDENTIFIER ::= { rcMgmt 227 }

-- LOGICAL (System) Elements

rcSysIpAddr OBJECT-TYPE
        SYNTAX        IpAddress
        MAX-ACCESS    read-only
        STATUS        current
        DESCRIPTION   "This entity's IP address."
        ::= { rcSystem 1 }

rcSysNetMask OBJECT-TYPE
        SYNTAX        IpAddress
        MAX-ACCESS    read-only
        STATUS        current
        DESCRIPTION   "This entity's subnet mask."
        ::= { rcSystem 2 }

rcSysBroadcast OBJECT-TYPE
        SYNTAX        IpAddress
        MAX-ACCESS    read-only
        STATUS        current
        DESCRIPTION   "This entity's broadcast address."
        ::= { rcSystem 3 }

-- Community Strings

rcSysCommReadWriteAll OBJECT-TYPE
        SYNTAX        DisplayString (SIZE (0..20))
        MAX-ACCESS    read-write
        STATUS        current
        DESCRIPTION   "When an SNMP message is received by this entity, the
                      community string in the message is compared with this
                      string first.  If it matches, read-write access is
                      granted to all items in the MIB.  If it doesn't
                      match, the rcSysCommReadWrite string is compared next."
        ::= { rcSystem 4 }

rcSysCommReadWrite OBJECT-TYPE
        SYNTAX        DisplayString (SIZE (0..20))
        MAX-ACCESS    read-write
        STATUS        current
        DESCRIPTION   "When an SNMP message is received by this entity, the
                      community string in the message is compared with this
                      string second.  If it matches, read-write access is
                      granted to all items in the MIB except community
                      strings.  (Community strings appear empty when read
                      and return a no such name error when an attempt is
                      made to write them.)  If it doesn't match, the
                      rcSysCommReadWriteLayer3 string is compared next."
        ::= { rcSystem 5 }

rcSysCommReadOnly OBJECT-TYPE
        SYNTAX        DisplayString (SIZE (0..20))
        MAX-ACCESS    read-write
        STATUS        current
        DESCRIPTION   "When an SNMP message is received by this entity, the
                      community string in the message is compared with this
                      string third.  If it matches, read-only access is
                      granted to all items in the MIB except community
                      strings.  (Community strings appear empty when read.)
                      If it doesn't match, no access is granted, no
                      response is sent back to the SNMP requester, and
                      SNMP traps are sent to the SNMP trap receiver(s) if
                      configured."
        ::= { rcSystem 6 }

-- Other

rcSysVersion OBJECT-TYPE
	SYNTAX 		DisplayString (SIZE (0..80))
	MAX-ACCESS 		read-only
	STATUS 		current
	DESCRIPTION	"Software version running on device"
	::= { rcSystem 7 }

rcSysAction OBJECT-TYPE
        SYNTAX       INTEGER {
                         none(1),               -- none of the following
                         hardReset(2),          -- power on tests
                         softReset(3),          -- reset w/o power on tests
                         saveToNVRAM(4),        -- save current config to NVRAM
                         resetCounters(5),      -- reset all statistic counters
                         saveToStandbyNVRAM(6), -- save config to slave NVRAM
                         cpuSwitchOver(7),      -- CPU board switch-over
		         checkSwInFlash(8),       
		         checkSwInPcmcia(9),
			 resetConsole(10),
			 resetModem(11),
			 flushIpRouteTbl(12),
			 saveRuntimeConfig(13),		-- 8k only
			 saveRuntimeConfigToSlave(14),	-- 8k only
			 saveBootConfig(15),		-- 8k only
			 saveSlaveBootConfig(16), 	-- 8k only
                         resetIstStatCounters(17),
--			 being used in rel2.2(18)
--			 being used in rel2.2(19)
--			 reserve(20)
--			 reserve(21)
                         resetEsmPortStats(22),
                         setCsuAuto(23)
 	              }
        MAX-ACCESS    read-write
        STATUS        deprecated
	DESCRIPTION   "Initiate a system action."
	DEFVAL 	      { none }
        ::= { rcSystem 8 }

rcSysResult OBJECT-TYPE
	SYNTAX       INTEGER {
		         none(1),		-- none of the following
		         inProgress(2),		-- in progress
		         success(3),		-- success
		         fail(4),		-- failure
		         flashReadFailed(5),	-- could not read from flash
		         pcmciaReadFailed(6),	-- could not read from pcmcia
		         crcCheckFailed(7),
                         noStandbyCpu(8)
	              }
        MAX-ACCESS    read-only
        STATUS        current
	DESCRIPTION   "Result from the last system action."
	DEFVAL 	      { none }
        ::= { rcSystem 9 }

rcSysLastChange OBJECT-TYPE
        SYNTAX        TimeTicks
        MAX-ACCESS    read-only
        STATUS        current
        DESCRIPTION   "Last management initiated configuration 
		      change since sysUpTime."
        ::= { rcSystem 10 }

rcSysLastVlanChange OBJECT-TYPE
        SYNTAX        TimeTicks
        MAX-ACCESS    read-only
        STATUS        current
        DESCRIPTION   "Last management initiated VLAN configuration 
		      change since sysUpTime."
        ::= { rcSystem 11 }

rcSysLastStatisticsReset OBJECT-TYPE
        SYNTAX        TimeTicks
        MAX-ACCESS    read-only
        STATUS        current
        DESCRIPTION   "Last management initiated statistics reset 
		      since sysUpTime."
        ::= { rcSystem 12 }

-- Global Statistics

rcSysBufferUtil OBJECT-TYPE
	SYNTAX        Integer32 (0..100)
	MAX-ACCESS    read-only
	STATUS        current
	DESCRIPTION   "Buffer utilization as a percentage of the
                      total amount of buffer space in the system.  
                      A high value indicates congestion."
	::= { rcSystem 13 }

rcSysBufferUtilPeak OBJECT-TYPE
	SYNTAX        Integer32 (0..100)
	MAX-ACCESS    read-only
	STATUS        current
	DESCRIPTION   "The largest buffer utilization since sysUpTime"
	::= { rcSystem 14 }

rcSysBufferUtilPeakTime OBJECT-TYPE
	SYNTAX        TimeTicks
	MAX-ACCESS    read-only
	STATUS        current
	DESCRIPTION   "Timestamp for rcSysPeakBandwidth"
	::= { rcSystem 15 }

rcSysNVRamSize OBJECT-TYPE
	SYNTAX        Gauge32
	MAX-ACCESS    read-only
	STATUS        current
	DESCRIPTION   "Total Non-volatile RAM in Kbytes"
	::= { rcSystem 16 }

rcSysNVRamUsed OBJECT-TYPE
	SYNTAX        Gauge32
	MAX-ACCESS    read-only
	STATUS        current
	DESCRIPTION   "Non-volatile RAM in use in Kbytes"
	::= { rcSystem 17 }

rcSysLastSaveToNVRam    OBJECT-TYPE
        SYNTAX        TimeTicks
        MAX-ACCESS    read-only
        STATUS        current
        DESCRIPTION   "SysUpTime of the last time when NVRAM was
                      written to.  This could be a save of the system
                      configuration or via a file transfer of a
                      configuration file."
        ::= { rcSystem 18 }

rcSysLastSaveToStandbyNVRam OBJECT-TYPE
        SYNTAX        TimeTicks
        MAX-ACCESS    read-only
        STATUS        current
        DESCRIPTION   "SysUpTime of the last time when the standby NVRAM
                      (on the back-up CPU board) was written to."
        ::= { rcSystem 19 }

rcSysCpuUtil OBJECT-TYPE
        SYNTAX        Gauge32
        MAX-ACCESS    read-only
        STATUS        current
        DESCRIPTION   "Percentage of CPU utilization"
        ::= { rcSystem 20 }

rcSysSwitchFabricUtil OBJECT-TYPE
        SYNTAX        Gauge32
        MAX-ACCESS    read-only
        STATUS        current
        DESCRIPTION   "Percentage of Switching Fabric utilization"
        ::= { rcSystem 21 }

rcSysRmonMemSize OBJECT-TYPE
        SYNTAX        Integer32 (250000..4000000)
        MAX-ACCESS    read-write
        STATUS        current
        DESCRIPTION   "Amount of RAM in bytes to allocate for RMON
                      to use when rcSysRmonEnable is TRUE."
        ::= { rcSystem 22 }

rcSysRmonEnable OBJECT-TYPE
        SYNTAX        TruthValue
        MAX-ACCESS    read-write
        STATUS        current
        DESCRIPTION   "Control whether the RMON feature should be
                      enabled.

		      To enable the RMON feature, set this variable to
		      true.  The RMON agent in the device will get 
                      started immediately if the amount of memory
		      specified by rcSysRmonMemSize is currently
		      available in the device.

		      To disable the RMON feature, set this variable to
		      false, save the new setting to NVRAM, and reboot
		      the device.  After the device is rebooted the
		      RMON agent will not be operational." 
        ::= { rcSystem 23 }

rcSysRmonSaveConfig OBJECT-TYPE
        SYNTAX        TruthValue
        MAX-ACCESS    read-write
        STATUS        deprecated
        DESCRIPTION   "Control whether RMON configuration information 
                      should be saved to NVRAM so RMON settings can 
                      be automatically reinstalled after a system
                      reboot. 

		      Setting rcSysRmonSaveConfig to true does not 
		      immediately save the configuration information.
		      The save happens when the rcSysAction variable 
		      is set to 'saveToNVRAM(4)'.

                      This option is only meaningful when the 
                      rcSysRmonEnable variable is set to true."
        ::= { rcSystem 24 }

rcSysRmonTrapOption OBJECT-TYPE
        SYNTAX        INTEGER {
		 	 toOwner(1),
			 toAll(2)
		      }
        MAX-ACCESS    read-write
        STATUS        current
        DESCRIPTION   "Used to indicate whether RMON traps should be
		      sent to only the owner of the RMON alarm (i.e.,
		      the manager that created the alarm entry) or 
		      all trap recipients in the system trap receiver
		      table."
	DEFVAL	      { toOwner }
        ::= { rcSystem 25 }

rcSysSupportRouting OBJECT-TYPE
        SYNTAX        TruthValue
        MAX-ACCESS    read-only
        STATUS        current
        DESCRIPTION   "Used to indicate whether routing is supported
                      in this product."
        ::= { rcSystem 26 }

rcSysSupportWebServer OBJECT-TYPE
        SYNTAX        TruthValue
        MAX-ACCESS    read-only
        STATUS        current
        DESCRIPTION   "Used to indicate whether WebServer is supported
                      in this product."
        ::= { rcSystem 27 }

rcSysLastIpAddrChange OBJECT-TYPE
        SYNTAX        TimeTicks
        MAX-ACCESS    read-only
        STATUS        current
        DESCRIPTION   "Last management initiated IP address change 
                       since sysUpTime.  Any addition or deletion of
                       an IP address to a single routable port or
                       a VLAN is time-stamped by this variable."
        ::= { rcSystem 28 }

rcSysCommReadWriteLayer3 OBJECT-TYPE
        SYNTAX        DisplayString (SIZE (0..20))
        MAX-ACCESS    read-write
        STATUS        current
        DESCRIPTION   "When an SNMP message is received by this entity, the
                      community string in the message is compared with this
                      string third.  If it matches, read-write access is 
		      granted to all Layer-3 items in the MIB except community
                      strings.  (Community strings appear empty when read
                      and return a no such name error when an attempt is
                      made to write them.)  If it doesn't match, the
                      rcSysCommReadWriteLayer2 string is compared next."
        ::= { rcSystem 29 }

rcSysCommReadWriteLayer2 OBJECT-TYPE 
        SYNTAX        DisplayString (SIZE (0..20)) 
        MAX-ACCESS    read-write 
        STATUS        current 
        DESCRIPTION   "When an SNMP message is received by this entity, the 
                      community string in the message is compared with this 
                      string fourth.  If it matches, read-write access is 
                      granted to all Layer-2 items in the MIB except community
                      strings.  (Community strings appear empty when read 
                      and return a no such name error when an attempt is
                      made to write them.)  If it doesn't match, the
                      rcSysCommReadOnly string is compared next." 
        ::= { rcSystem 30 }

rcSysAccessPolicyEnable OBJECT-TYPE
        SYNTAX        TruthValue
        MAX-ACCESS    read-write
        STATUS        current
        DESCRIPTION   "Used to configure the system access policy feature.
		      if 'true', the rcSysAccessPolicyTable is examined to
		      determine which packets should be allowed or denied
                      access to this device." 
	DEFVAL	      { false }
        ::= { rcSystem 31 }

rcSysDefaultRuntimeConfigFileName OBJECT-TYPE
        SYNTAX        DisplayString
        MAX-ACCESS    read-only
        STATUS        current
        DESCRIPTION   "default config."
        ::= { rcSystem 32 }
 
rcSysDefaultBootConfigFileName OBJECT-TYPE
        SYNTAX        DisplayString
        MAX-ACCESS    read-only
        STATUS        current
        DESCRIPTION   "default boot config."
        ::= { rcSystem 33 }
 
rcSysConfigFileName OBJECT-TYPE
        SYNTAX        	DisplayString (SIZE(0..255))
        MAX-ACCESS        	read-write
        STATUS        	current
        DESCRIPTION   	"File name used in conjunction with rcSysAction.

			If rcSysAction is set to 'saveRuntimeConfig' or
			'saveRuntimeConfigToSlave' then this file name
			will be used instead of the file name specified
			in rcSysDefaultRuntimeConfigFileName.  

			If rcSysAction is set to 'saveBootConfig' or
			'saveBootConfigToSlave' then this file name will
			be used insteaad of the file name specified in
			rcSysDefaultBootConfigFileName.

			If the file name is blank (i.e., nothing is
			entered) then the default file name will be
			used."
        ::= { rcSystem 34 }
 
rcSysLastRunTimeConfigSave OBJECT-TYPE
        SYNTAX        TimeTicks
        MAX-ACCESS    read-only
        STATUS        current
        DESCRIPTION   "SysUpTime of the last time when the run time
                      configuration was written to."
        ::= { rcSystem 35 }

rcSysLastRunTimeConfigSaveToSlave OBJECT-TYPE
        SYNTAX        TimeTicks
        MAX-ACCESS    read-only
        STATUS        current
        DESCRIPTION   "SysUpTime of the last time when the run time
                      configuration was written to slave NVRAM."
        ::= { rcSystem 36 }

rcSysLastBootConfigSave OBJECT-TYPE
        SYNTAX        TimeTicks
        MAX-ACCESS    read-only
        STATUS        current
        DESCRIPTION   "SysUpTime of the last time when the boot
                      configuration was written to."
        ::= { rcSystem 37 }

rcSysLastBootConfigSaveOnSlave OBJECT-TYPE
        SYNTAX        TimeTicks
        MAX-ACCESS    read-only
        STATUS        current
        DESCRIPTION   "SysUpTime of the last time when the boot
                      configuration was written on the slave NVRAM."
        ::= { rcSystem 38 }

rcSysRmonUtilizationMethod OBJECT-TYPE	--excluded
        SYNTAX        INTEGER {
                         halfDuplex(1),
                         fullDuplex(2)
                      }
        MAX-ACCESS    read-write
        STATUS        current
        DESCRIPTION   "Used to control whether RMON should use a half-duplex
                       or full-duplex formula to calculate port utilization.
                       When set to 'halfDuplex', RMON will use InOctets and
                       the port's speed to calculate port utilization (this
                       is the standard RMON rfc1271 convention).
                       When set to 'fullDuplex', RMON will use InOctets and
                       OutOctets and 2X the port's speed to calculate port
                       utilization. Furthermore, if this variable is set to
                       'fullDuplex', but the port is operating in a
                       half-duplex mode, the calculation defaults back to
                       the rfc1271 convention."
        DEFVAL        { halfDuplex }
        ::= { rcSystem 39 }
 
rcSysCommReadWriteLayer1 OBJECT-TYPE
        SYNTAX        DisplayString (SIZE (0..20))
        MAX-ACCESS    read-write
        STATUS        current
        DESCRIPTION   "read-write L1 access"
        ::= { rcSystem 40 }

rcSysOtherBufferUtil OBJECT-TYPE
        SYNTAX        Gauge32
        MAX-ACCESS    read-only
        STATUS        current
        DESCRIPTION   "bw currently consumed"
        ::= { rcSystem 41 }
 
rcSysOtherBufferUtilPeak OBJECT-TYPE
        SYNTAX        Gauge32
        MAX-ACCESS    read-only
        STATUS        current
        DESCRIPTION   "peak bw since reset"
        ::= { rcSystem 42 }

rcSysOtherBufferUtilPeakTime OBJECT-TYPE
        SYNTAX        TimeTicks
        MAX-ACCESS    read-only
        STATUS        current
        DESCRIPTION   "timestamp for rcSysPeakBw"
        ::= { rcSystem 43 }
 
rcSysOtherCpuUtil OBJECT-TYPE
        SYNTAX        Gauge32
        MAX-ACCESS    read-only
        STATUS        current
        DESCRIPTION   "% cpu utilization"
        ::= { rcSystem 44 }

rcSysOtherSwitchFabricUtil OBJECT-TYPE
        SYNTAX        Gauge32
        MAX-ACCESS    read-only
        STATUS        current
        DESCRIPTION   "% switch fabric util"
        ::= { rcSystem 45 }

rcSysDramSize OBJECT-TYPE
        SYNTAX        Integer32
        MAX-ACCESS    read-only
        STATUS        current
        DESCRIPTION   "Dram size in mega-bytes"
        ::= { rcSystem 46 }
 
rcSysDramUsed OBJECT-TYPE
        SYNTAX        Gauge32
        MAX-ACCESS    read-only
        STATUS        current
        DESCRIPTION   "Dram used in percentage"
        ::= { rcSystem 47 }
 
rcSysDramFree OBJECT-TYPE
        SYNTAX        Integer32
        MAX-ACCESS    read-only
        STATUS        current
        DESCRIPTION   "Dram free size in kilo-bytes"
        ::= { rcSystem 48 }
 
rcSysDramMaxBlockFree OBJECT-TYPE
        SYNTAX        Integer32
        MAX-ACCESS    read-only
        STATUS        current
        DESCRIPTION   "Dram max block free size in kilo-bytes"
        ::= { rcSystem 49 }
 
rcSysVirtualIpAddr OBJECT-TYPE
        SYNTAX        IpAddress
        MAX-ACCESS    read-write
        STATUS        current
        DESCRIPTION   "Virtual IP is an IP address that owned and
		       advertised only by the master CPU. So whichever 
		       CPU is master registers this IP address. Unlike the
		       management IP address, this address goes in the 
		       switch config file and not the boot config"
        ::= { rcSystem 51 }
 
rcSysVirtualNetMask OBJECT-TYPE
        SYNTAX        IpAddress
        MAX-ACCESS    read-write
        STATUS        current
        DESCRIPTION   "Net mask of the management virtual Ip address"
        ::= { rcSystem 52 }
 
rcSysReadWriteLevel OBJECT-TYPE
        SYNTAX        Integer32
        MAX-ACCESS    read-write
        STATUS        current
        DESCRIPTION   "The status of the read/write level"
        ::= { rcSystem 53 }

rcSysMTUSize OBJECT-TYPE
        SYNTAX        INTEGER {
                         mtu1950(1),
                         mtu9600(2),
                         mtu1522(3)
                      }
        MAX-ACCESS    read-write
        STATUS        current
        DESCRIPTION   "This is the maximum transmission size of frames that all
                       the ports on the chassis support."
        DEFVAL   { mtu1950 }
        ::= { rcSystem 55 }

rcSysClockSyncTime OBJECT-TYPE
        SYNTAX        Integer32 (15..3600)
        MAX-ACCESS    read-write
        STATUS        current
        DESCRIPTION   "Time interval at which RTC and system clocks are
                       synchronized."
        DEFVAL   { 60 }
        ::= { rcSystem 56 }

rcSysForceTrapSender OBJECT-TYPE
        SYNTAX        TruthValue
        MAX-ACCESS    read-write
        STATUS        current
        DESCRIPTION   "This is a flag that if user wants to configured
                       CLIP (Circuit Less IP) as trap originator."
        ::= { rcSystem 57 }

rcSysMrouteStrLimit OBJECT-TYPE
        SYNTAX        TruthValue
        MAX-ACCESS    read-write
        STATUS        current
        DESCRIPTION   "enable or disable mroute stream limit in system."
        DEFVAL        { false }
        ::= { rcSystem 58 }

-- Trap Receiver Table
 
rcSysTrapRecvTable OBJECT-TYPE
        SYNTAX        SEQUENCE OF RcSysTrapRecvEntry
        MAX-ACCESS    not-accessible
        STATUS        deprecated
        DESCRIPTION   "The trap receiver table (0 to 25 entries).  This
                      table lists the addresses of Network Management
                      Stations that should receive trap messages from 
                      this entity when an exception condition occurs."
        ::= { rcSystem 60 }

rcSysTrapRecvEntry OBJECT-TYPE
        SYNTAX        RcSysTrapRecvEntry
        MAX-ACCESS    not-accessible
        STATUS        deprecated
        DESCRIPTION   "A trap receiver table entry."
        INDEX         { rcSysTrapRecvAddress }
        ::= { rcSysTrapRecvTable 1 }
 
RcSysTrapRecvEntry ::=
        SEQUENCE {
                rcSysTrapRecvAddress IpAddress,
                rcSysTrapRecvVersion INTEGER,
                rcSysTrapRecvCommunity DisplayString,
                rcSysTrapRecvSrcAddress IpAddress,
                rcSysTrapRecvRowStatus RowStatus
        }
 
rcSysTrapRecvAddress OBJECT-TYPE
        SYNTAX        IpAddress
        MAX-ACCESS    read-only
        STATUS        deprecated
        DESCRIPTION   "IP address for trap receiver."
        ::= { rcSysTrapRecvEntry 1 }
 
rcSysTrapRecvVersion OBJECT-TYPE
        SYNTAX        INTEGER {
                         v1(1),          
                         v2c(2)
                      }
        MAX-ACCESS    read-write
        STATUS	      deprecated
        DESCRIPTION   "The version of trap receiver."
        DEFVAL 	      { v1 }
	::= { rcSysTrapRecvEntry 2 }

rcSysTrapRecvCommunity OBJECT-TYPE
        SYNTAX        DisplayString (SIZE (0..20))
        MAX-ACCESS    read-write
        STATUS        deprecated
        DESCRIPTION   "Community string used for trap messages to this
                       trap receiver."
        ::= { rcSysTrapRecvEntry 3 }

rcSysTrapRecvSrcAddress OBJECT-TYPE 
        SYNTAX        IpAddress
        MAX-ACCESS    read-write
        STATUS        deprecated
        DESCRIPTION   "Source IP address to use when sending traps.
		       This IP address will be inserted into the
		       source IP address field in the UDP trap packet."
        ::= { rcSysTrapRecvEntry 4 } 
 
rcSysTrapRecvRowStatus OBJECT-TYPE
        SYNTAX        RowStatus
        MAX-ACCESS    read-write
        STATUS        deprecated
        DESCRIPTION   "Used to create/delete entries"
        ::= { rcSysTrapRecvEntry 5 }


-- Access Policy Table
 
rcSysAccessPolicyTable OBJECT-TYPE
        SYNTAX        SEQUENCE OF RcSysAccesspolicyEntry
        MAX-ACCESS    not-accessible
        STATUS        current
        DESCRIPTION   "Management access policy table.  This table is 
		       used to permit or deny access to this device via
		       the specified source Id."
        ::= { rcSystem 61 }

rcSysAccessPolicyEntry OBJECT-TYPE
        SYNTAX        RcSysAccesspolicyEntry
        MAX-ACCESS    not-accessible
        STATUS        current
        DESCRIPTION   "An access policy table entry."
        INDEX         { rcSysAccessPolicyId }
        ::= { rcSysAccessPolicyTable 1 }
 
RcSysAccesspolicyEntry ::=
        SEQUENCE {
                rcSysAccessPolicyId Integer32,
                rcSysAccessPolicyName DisplayString,
                rcSysAccessPolicyPolicyEnable TruthValue,
                rcSysAccessPolicyMode INTEGER,
                rcSysAccessPolicyService Integer32,
                rcSysAccessPolicyPrecedence Integer32,
                rcSysAccessPolicyNetAddr IpAddress,
                rcSysAccessPolicyNetMask IpAddress,
                rcSysAccessPolicyTrustedHostAddr IpAddress,
                rcSysAccessPolicyTrustedHostUserName DisplayString,
                rcSysAccessPolicyAccessLevel INTEGER,
                rcSysAccessPolicyLog TruthValue,
                rcSysAccessPolicyUsage Counter32,
                rcSysAccessPolicyRowStatus RowStatus,
                rcSysAccessPolicyAccessStrict TruthValue,
		rcSysAccessPolicyNetInetAddrType INTEGER,
                rcSysAccessPolicyNetInetAddress InetAddress,
                rcSysAccessPolicyNetInetAddrPrefixLen InetAddressPrefixLength,
                rcSysAccessPolicyTrustedHostInetAddress InetAddress
        }
 
rcSysAccessPolicyId OBJECT-TYPE 
        SYNTAX        Integer32 (1..65535)
        MAX-ACCESS    read-only
        STATUS        current
        DESCRIPTION   "Policy Id."
        ::= { rcSysAccessPolicyEntry 1 } 

rcSysAccessPolicyName OBJECT-TYPE
        SYNTAX        DisplayString (SIZE (0..15))
        MAX-ACCESS    read-write
        STATUS        current
        DESCRIPTION   "Name of this policy."
        ::= { rcSysAccessPolicyEntry 2 }

rcSysAccessPolicyPolicyEnable OBJECT-TYPE
        SYNTAX        TruthValue
        MAX-ACCESS    read-write
        STATUS        current
        DESCRIPTION   "Indicate whether this policy is currently 
                       active."
	DEFVAL	      { true }
        ::= { rcSysAccessPolicyEntry 3 }

rcSysAccessPolicyMode OBJECT-TYPE
        SYNTAX        INTEGER {
                        allow(1), 
                        deny(2)
                      }          
        MAX-ACCESS    read-write
        STATUS        current
        DESCRIPTION   "Used to indicate whether a packet having a
		       source IP address that matches this entry
		       should be permitted to enter the device or
 		       denied access." 
	DEFVAL	      { allow }
        ::= { rcSysAccessPolicyEntry 4 }

rcSysAccessPolicyService OBJECT-TYPE
        SYNTAX        Integer32 (0..255)
        MAX-ACCESS    read-write
        STATUS        current
        DESCRIPTION   "Is represented as bitset to indicate which protocol
                      this entry should be applied to.
                      Value is one of multiple(logical 'OR')
                      of the following values: 
                      telnet(1): enables telnet service
                      snmp(2): enables snmp service
                      tftp(4): enables tftp service
                      ftp(8): enables ftp service
                      http(16): enables http service
                      rlogin(32): enables rlogin service
                      ssh(64): enables ssh service
                      snmp-v3(128): enables snmp service for v3 groups."
        ::= { rcSysAccessPolicyEntry 5 }

rcSysAccessPolicyPrecedence OBJECT-TYPE
        SYNTAX        Integer32 (1..128)
        MAX-ACCESS    read-write
        STATUS        current
        DESCRIPTION   "Used to indicate the precedence of this policy.
		       The Lower the number the higher the precedence."
	DEFVAL	      { 10 }
        ::= { rcSysAccessPolicyEntry 6 }

rcSysAccessPolicyNetAddr OBJECT-TYPE
        SYNTAX        IpAddress
        MAX-ACCESS    read-write
        STATUS        current
        DESCRIPTION   "Source network IP address."
        ::= { rcSysAccessPolicyEntry 7 }
 
rcSysAccessPolicyNetMask OBJECT-TYPE
        SYNTAX        IpAddress
        MAX-ACCESS    read-write
        STATUS        current
        DESCRIPTION   "Source network mask."
        ::= { rcSysAccessPolicyEntry 8 }
 
rcSysAccessPolicyTrustedHostAddr OBJECT-TYPE
        SYNTAX        IpAddress
        MAX-ACCESS    read-write
        STATUS        current
        DESCRIPTION   "Trusted IP address of host performing a rlogin
		       into the device."
        ::= { rcSysAccessPolicyEntry 9 }
 
rcSysAccessPolicyTrustedHostUserName OBJECT-TYPE
        SYNTAX        DisplayString (SIZE (0..30))
        MAX-ACCESS    read-write
        STATUS        current
        DESCRIPTION   "User name on the trusted host performing a rlogin
                       into the device."
        ::= { rcSysAccessPolicyEntry 10 }

rcSysAccessPolicyAccessLevel OBJECT-TYPE
        SYNTAX        INTEGER {
                        readOnly(1), 
                        readWrite(2),
                        readWriteAll(3)
                      }          
        MAX-ACCESS    read-write
        STATUS        current
        DESCRIPTION   "Access level of trusted host." 
	DEFVAL	      { readOnly }
        ::= { rcSysAccessPolicyEntry 11 }

rcSysAccessPolicyLog OBJECT-TYPE
        SYNTAX        TruthValue
        MAX-ACCESS    read-write
        STATUS        current
        DESCRIPTION   "Used to indicate whether logging should be 
		       performed if this policy was applied."
	DEFVAL	      { false }
        ::= { rcSysAccessPolicyEntry 12 }

rcSysAccessPolicyUsage OBJECT-TYPE
        SYNTAX  	Counter32
        MAX-ACCESS  	read-only
        STATUS  	current
        DESCRIPTION 	"Usage Counter"
        ::= { rcSysAccessPolicyEntry 13 }

rcSysAccessPolicyRowStatus OBJECT-TYPE
        SYNTAX        RowStatus
        MAX-ACCESS    read-write
        STATUS        current
        DESCRIPTION   "Used to create/delete an entry"
        ::= { rcSysAccessPolicyEntry 14 }

rcSysAccessPolicyAccessStrict OBJECT-TYPE
        SYNTAX        TruthValue
        MAX-ACCESS    read-write
        STATUS        current
        DESCRIPTION   "Used to restrict the access level specified in
                       the system access policy table to exactly the
                       same access level as specified by user. If TRUE
                       then only the access level in the policy table
                       is allowed access. If FALSE, then the default
                       behavior is to assume the access level specified
                       in policy table as the floor."
          DEFVAL        { false }
        ::= { rcSysAccessPolicyEntry 15 }

rcSysAccessPolicyNetInetAddrType OBJECT-TYPE
        SYNTAX        INTEGER {
                                  any(0),
                                  ipv4(1),
                                  ipv6(2)
                              }
        MAX-ACCESS    read-write
        STATUS        current
        DESCRIPTION   "Source network Inet Address Type."
        ::= { rcSysAccessPolicyEntry 16 }

rcSysAccessPolicyNetInetAddress OBJECT-TYPE
        SYNTAX        InetAddress
        MAX-ACCESS    read-write
        STATUS        current
        DESCRIPTION   "Source network Inet Address (prefix/network)."
        ::= { rcSysAccessPolicyEntry 17 }

rcSysAccessPolicyNetInetAddrPrefixLen OBJECT-TYPE
        SYNTAX        InetAddressPrefixLength
        MAX-ACCESS    read-write
        STATUS        current
        DESCRIPTION   "Source network Inet Address Prefix-Length/Mask."
        ::= { rcSysAccessPolicyEntry 18 }

rcSysAccessPolicyTrustedHostInetAddress OBJECT-TYPE
        SYNTAX        InetAddress
        MAX-ACCESS    read-write
        STATUS        current
        DESCRIPTION   "Trusted Inet address of host performing a rlogin
                       into the device."
        ::= { rcSysAccessPolicyEntry 19 }


-- Trap Sender Address Table

rcSysTrapSenderTable OBJECT-TYPE
        SYNTAX        SEQUENCE OF RcSysTrapSenderEntry
        MAX-ACCESS    not-accessible
        STATUS        current
        DESCRIPTION   "The trap sender table (0 to 25 entries).  This
                      table lists the addresses of Network Management
                      Stations and the Source Address that should receive
                      trap messages from this entity when an exception
                      condition occurs."
        ::= { rcSystem 62 }

rcSysTrapSenderEntry OBJECT-TYPE
        SYNTAX        RcSysTrapSenderEntry
        MAX-ACCESS    not-accessible
        STATUS        current
        DESCRIPTION   "A trap sender table entry."
        INDEX         { rcSysTrapSenderRecvAddress }
        ::= { rcSysTrapSenderTable 1 }

RcSysTrapSenderEntry ::=
        SEQUENCE {
                rcSysTrapSenderRecvAddress IpAddress,
                rcSysTrapSenderSrcAddress  IpAddress
        }

rcSysTrapSenderRecvAddress OBJECT-TYPE
        SYNTAX        IpAddress
        MAX-ACCESS    read-only
        STATUS        current
        DESCRIPTION   "IP address for trap receiver."
        ::= { rcSysTrapSenderEntry 1 }

rcSysTrapSenderSrcAddress OBJECT-TYPE
        SYNTAX        IpAddress
        MAX-ACCESS    read-write
        STATUS       current
        DESCRIPTION   "IP address for trap sender."
          ::= { rcSysTrapSenderEntry 2 }


-- DNS Server List Mibs

rcSysDnsServerListTableSize OBJECT-TYPE
        SYNTAX          Integer32
        MAX-ACCESS      read-only
        STATUS          current
        DESCRIPTION     "Used to indicate the number of entries in the
                         table."
        ::= { rcSystem 63 }

rcSysDnsServerListTable OBJECT-TYPE
        SYNTAX        SEQUENCE OF RcSysDnsServerListEntry
        MAX-ACCESS    not-accessible
        STATUS        current
        DESCRIPTION   "DNS serever list table used to store the
                       details of the DNS server configured."
        ::= { rcSystem 64 }

rcSysDnsServerListEntry OBJECT-TYPE
        SYNTAX        RcSysDnsServerListEntry
        MAX-ACCESS    not-accessible
        STATUS        current
        DESCRIPTION   "table entry."
        INDEX         {rcSysDnsServerListType}
        ::= { rcSysDnsServerListTable 1 }

RcSysDnsServerListEntry ::=
        SEQUENCE {
                rcSysDnsServerListType          INTEGER,
                rcSysDnsServerListIp            IpAddress, -- deprecated
                rcSysDnsServerListStatus        INTEGER,
                rcSysDnsServerListRequestCount  Counter32,
                rcSysDnsServerListSuccessCount  Counter32,
                rcSysDnsServerListRowStatus     RowStatus,
                rcSysDnsServerListAddressType     InetAddressType,
                rcSysDnsServerListAddress     InetAddress
        }

rcSysDnsServerListType OBJECT-TYPE
        SYNTAX        INTEGER {
                         primary(0),
                         secondary(1),
                         tertiary(2),
			 dynamic(3)
                      }
        MAX-ACCESS    read-write
        STATUS        current
        DESCRIPTION   "Type of the DNS server"
        ::= { rcSysDnsServerListEntry 1 }

rcSysDnsServerListIp OBJECT-TYPE
        SYNTAX        IpAddress
        MAX-ACCESS    read-write
        STATUS        deprecated
        DESCRIPTION   "IP address of the DNS server"
        ::= { rcSysDnsServerListEntry 2 }

rcSysDnsServerListStatus OBJECT-TYPE
        SYNTAX        INTEGER {
                         active(0),
                         in-active(1)
                      }
        MAX-ACCESS    read-only
        STATUS        current
        DESCRIPTION   "Status of DNS server"
        ::= { rcSysDnsServerListEntry 3 }

rcSysDnsServerListRequestCount OBJECT-TYPE
        SYNTAX        Counter32
        MAX-ACCESS    read-only
        STATUS        current
        DESCRIPTION   "Number of request send to this server"
        ::= { rcSysDnsServerListEntry 4 }

rcSysDnsServerListSuccessCount OBJECT-TYPE
        SYNTAX        Counter32
        MAX-ACCESS    read-only
        STATUS        current
        DESCRIPTION   "Number of request send to this server which
                       are successful"
        ::= { rcSysDnsServerListEntry 5 }

rcSysDnsServerListRowStatus OBJECT-TYPE
        SYNTAX        RowStatus
        MAX-ACCESS    read-write
        STATUS        current
        DESCRIPTION   "Used to create/delete DNS server entries
                       in rcSysDnsServerListTable."
        ::= { rcSysDnsServerListEntry 6 }

rcSysDnsServerListAddressType  OBJECT-TYPE
        SYNTAX        InetAddressType
        MAX-ACCESS    read-create
        STATUS        current
        DESCRIPTION   "The type of ip address configured by the DNS server"
        ::= { rcSysDnsServerListEntry 7 }

rcSysDnsServerListAddress  OBJECT-TYPE
        SYNTAX        InetAddress
        MAX-ACCESS    read-create
        STATUS        current
        DESCRIPTION   "The ip address configured by the DNS server"
        ::= { rcSysDnsServerListEntry 8 }

-- DNS Host Table

rcSysDnsHostTable OBJECT-TYPE
        SYNTAX        SEQUENCE OF RcSysDnsHostEntry
        MAX-ACCESS    not-accessible
        STATUS        current
        DESCRIPTION   "DNS Host table."
        ::= { rcSystem 65 }

rcSysDnsHostEntry OBJECT-TYPE
        SYNTAX        RcSysDnsHostEntry
        MAX-ACCESS    not-accessible
        STATUS        current
        DESCRIPTION   "table entry."
        INDEX         { rcSysDnsHostData }
        ::= { rcSysDnsHostTable 1 }

RcSysDnsHostEntry ::=
        SEQUENCE {
                rcSysDnsHostData          OCTET STRING,
                rcSysDnsHostName          OCTET STRING,
                rcSysDnsHostIpAddress     IpAddress,  -- deprecated
                rcSysDnsHostSource        OCTET STRING,
                rcSysDnsHostAddressType    InetAddressType,
                rcSysDnsHostAddress       InetAddress
        }

rcSysDnsHostData OBJECT-TYPE
        SYNTAX        OCTET STRING (SIZE(0..256))
        MAX-ACCESS    read-only
        STATUS        current
        DESCRIPTION   "Host Name or Host IP Address."
        ::= { rcSysDnsHostEntry 1 }

rcSysDnsHostName OBJECT-TYPE
        SYNTAX        OCTET STRING (SIZE(0..256))
        MAX-ACCESS    read-only
        STATUS        current
        DESCRIPTION   "Host Name."
        ::= { rcSysDnsHostEntry 2 }

rcSysDnsHostIpAddress OBJECT-TYPE
        SYNTAX        IpAddress
        MAX-ACCESS    read-only
        STATUS        deprecated
        DESCRIPTION   "Host IP Address."
        ::= { rcSysDnsHostEntry 3 }

rcSysDnsHostSource OBJECT-TYPE
        SYNTAX        OCTET STRING (SIZE(0..256))
        MAX-ACCESS    read-only
        STATUS        current
        DESCRIPTION   "DNS Server IP or /etc/host file."
        ::= { rcSysDnsHostEntry 4 }

rcSysDnsHostAddressType OBJECT-TYPE
        SYNTAX        InetAddressType
        MAX-ACCESS    read-only
        STATUS        current
        DESCRIPTION   "The type of ip address for the DNS host"
        ::= { rcSysDnsHostEntry 5 }

rcSysDnsHostAddress OBJECT-TYPE
        SYNTAX        InetAddress
        MAX-ACCESS    read-only
        STATUS        current
        DESCRIPTION   "The ip address of the DNS host"
        ::= { rcSysDnsHostEntry 6 }

rcSysMsgLogFrequency OBJECT-TYPE
        SYNTAX        Integer32 (2..500)
        MAX-ACCESS    read-only
        STATUS        current
        DESCRIPTION   "Used to specify the maximum frequency/count
                       of the occurence of the Log Message."
        ::= { rcSystem 66 }

rcSysMsgLogText OBJECT-TYPE
        SYNTAX        DisplayString (SIZE(0..3))
        MAX-ACCESS    read-only
        STATUS        current
        DESCRIPTION   "A textual string containing the first four
                       characters of the Log Message."
        ::= { rcSystem 67 }

rcSysForceIpHdrSender OBJECT-TYPE
        SYNTAX        TruthValue
        MAX-ACCESS    read-write
        STATUS        current
        DESCRIPTION   "Flag to decide if IP header source address will
                       be matched with SNMP header sender networks."
        DEFVAL        { false }
        ::= { rcSystem 68 }

rcSysVlanMaxId OBJECT-TYPE
        SYNTAX        INTEGER {
                         maxId2000(2000),
                         maxId4000(4000)
                      }
        MAX-ACCESS    read-only
        STATUS        current
        DESCRIPTION   "The maximum vlan Id that supported"
        DEFVAL        { maxId2000 }
        ::= { rcSystem 69 }

rcSysDnsDomainName OBJECT-TYPE
        SYNTAX        DisplayString (SIZE (0..255))
        MAX-ACCESS    read-write
        STATUS        current
        DESCRIPTION   "Default domain used for querying the DNS Server."
        ::= { rcSystem 70 }


rcSysDnsServerListIpAddr OBJECT-TYPE
        SYNTAX        IpAddress
        MAX-ACCESS    read-only
        STATUS        current
        DESCRIPTION   "DNS server's IP address "
        ::= { rcSystem 71 }

rcSysDnsRequestType OBJECT-TYPE
        SYNTAX        INTEGER {
                      request (0),
                      response (1)
                      }
        MAX-ACCESS    read-only
        STATUS        current
        DESCRIPTION   "DNS Type: Whether it was Dns Request or a Response"
        ::= { rcSystem 72 }


rcSysSpanningTreeOperMode OBJECT-TYPE
        SYNTAX        INTEGER {
                     nortelStpg(1), 
                     pvst(2), 
                     rstp(3), 
                     mstp(4) 
                    } 
          MAX-ACCESS   read-only 
          STATUS    current 
          DESCRIPTION  "This object indicates the current spanning-tree mode of the system. . 
                 The meaning of specific values is: 
                  nortelStpg(1) .. The older proprietary mode which supports multiple spanning tree groups. 
                  pvst(2) ........ Emulation of C***O spanning tree mode 
                  rstp(3) ........ IEEE 802.1w mode 
                  mstp(4) ........ IEEE 802.1s mode ." 
          DEFVAL        { nortelStpg }
            ::= { rcSystem 73} 

rcSysSpanningTreeAdminMode OBJECT-TYPE 
        SYNTAX        INTEGER {
                     nortelStpg(1), 
                     pvst(2), 
                     rstp(3), 
                     mstp(4) 
                    } 
          MAX-ACCESS   read-write 
          STATUS    current 
          DESCRIPTION  "This object indicates the desired spanning-tree mode of the system. 
                 The meaning of specific values is: 
                  nortelStpg(1) .. The older proprietary mode which supports multiple spanning tree groups. 
                  pvst(2) ........ Emulation of C***O spanning tree mode 
                  rstp(3) ........ IEEE 802.1w mode 
                  mstp(4) ........ IEEE 802.1s mode 

                Note that depending on the current value of rcSysSpanningTreeOperMode and 
                the value to which this object is set, the operational mode may be immediately changed, 
                or the change may not take effect until the next system reboot." 
           DEFVAL        { nortelStpg }
            ::= { rcSystem 74} 

rcSysAutoRecoverDelay  OBJECT-TYPE
        SYNTAX        Integer32 (5..3600)
        MAX-ACCESS    read-write
        STATUS        current
        DESCRIPTION  "Time interval in seconds after which auto-recovery
                      runs on ports to clear action taken by cp-limit, 
                      link flap or loop detect"
        DEFVAL { 30 }
        ::= { rcSystem 75 }

rcSysMacFlapLimitTime  OBJECT-TYPE
        SYNTAX        Integer32 (10..5000)
        MAX-ACCESS    read-write
        STATUS        current
        DESCRIPTION  "Time limit in milliseconds for MAC flapping for
                      loop-detect feature"
        ::= { rcSystem 76 }

rcSysMacFlapLimitCount  OBJECT-TYPE
        SYNTAX        Integer32
        MAX-ACCESS    read-only
        STATUS        current
        DESCRIPTION  "Number of times mac flapping can happen for loop-detect
                      feature"
        ::= { rcSystem 77 }

rcSysExtCplimitEnable  OBJECT-TYPE
        SYNTAX        TruthValue
        MAX-ACCESS    read-write
        STATUS        current
        DESCRIPTION   "enable or disable extended CP-LIMIT in system."
        DEFVAL        { false } 
        ::= { rcSystem 78 }

rcSysExtCplimitMinCongTime  OBJECT-TYPE
        SYNTAX        Integer32 (100..6000)
        MAX-ACCESS    read-write
        STATUS        current
        DESCRIPTION   "Minimum time for which System octapid should be
                      congested to trigger congestion algorithm for extended 
                      CP-LIMIT in mSecs"
        DEFVAL        { 3000 } 
        ::= { rcSystem 79 } 

rcSysExtCplimitMaxPorts  OBJECT-TYPE
        SYNTAX        Integer32 (0..512)
        MAX-ACCESS    read-write
        STATUS        current
        DESCRIPTION   "Maximum number of ports which need to be monitored
                      for congestion in Extended CP-LIMIT"
        DEFVAL        { 0 } 
        ::= { rcSystem 80 }

rcSysExtCplimitPortCongTime  OBJECT-TYPE
        SYNTAX        Integer32 (1..600)
        MAX-ACCESS    read-write
        STATUS        current
        DESCRIPTION   "Minimum time for which ingress traffic utilization rate 
                      of a monitored port should stay more than the allowed limits 
                      in order to disable the port for extended CP-LIMIT in Secs"
        DEFVAL        { 300 } 
        ::= { rcSystem 81 }

rcSysExtCplimitTrapLevel  OBJECT-TYPE
        SYNTAX        INTEGER {
                         none(1),
                         normal(2),
                         verbose(3)
                      }        
        MAX-ACCESS    read-write
        STATUS        current
        DESCRIPTION   "Indicates the trap level for extended CP-LIMIT"
        DEFVAL        { none }
        ::= { rcSystem 82 }

rcSysExtCplimitSysOctapidCongested OBJECT-TYPE
         SYNTAX        TruthValue
         MAX-ACCESS    read-only
         STATUS        current
         DESCRIPTION   "Indicates whether system octapid congestion detected for
                       extended cp-limit"
         DEFVAL        { false }
         ::= {rcSystem 83 }
 
 rcSysExtCplimitPortsMonitored OBJECT-TYPE
         SYNTAX        TruthValue
         MAX-ACCESS    read-only
         STATUS        current
         DESCRIPTION   "Indicates whether ports has been shutdown due to extended
                       cp-limit"
         DEFVAL        { false }
         ::= {rcSystem 84 }
 
 rcSysExtCplimitPortsShutDown OBJECT-TYPE
         SYNTAX        TruthValue
         MAX-ACCESS    read-only
         STATUS        current
         DESCRIPTION   "Indicates whether ports has been shutdown due to
                       extended Cp-limit"
         DEFVAL        { false }
         ::= {rcSystem 85 }

rcSysActionL1 OBJECT-TYPE
        SYNTAX       INTEGER {
                         none(1),
                         resetCounters(2),      -- reset all statistic counters
                         saveToNVRAM(3),
                         saveToStandbyNVRAM(4), -- save config to slave NVRAM
                         checkSwInFlash(5),
                         checkSwInPcmcia(6),
                         saveRuntimeConfig(7),     -- 8k only
                         saveRuntimeConfigToSlave(8),  -- 8k only
                         saveBootConfig(9),        -- 8k only
                         saveSlaveBootConfig(10),   -- 8k only
                         loadLicense(11)
                     }
        MAX-ACCESS    read-write
        STATUS        current
        DESCRIPTION   "Initiate a system action for layer1 user"
        DEFVAL        { none }
        ::= { rcSystem 86 }

rcSysActionL2 OBJECT-TYPE
        SYNTAX       INTEGER {
                         none(1),
                         resetIstStatCounters(2)
                     }
        MAX-ACCESS    read-write
        STATUS        current
        DESCRIPTION   "Initiate a system action for layer2 user"
        DEFVAL        { none }
        ::= { rcSystem 87 }

rcSysActionL3 OBJECT-TYPE
        SYNTAX       INTEGER {
                         none(1),
                         flushIpRouteTbl(2)
                     }
        MAX-ACCESS    read-write
        STATUS        current
        DESCRIPTION   "Initiate a system action for layer2 user"
        DEFVAL        { none }
        ::= { rcSystem 88 }

rcSysActionRwa OBJECT-TYPE
        SYNTAX       INTEGER {
                         none(1),               -- none of the following
                         hardReset(2),          -- power on tests
                         softReset(3),          -- reset w/o power on tests
                         cpuSwitchOver(4),      -- CPU board switch-over
                         resetConsole(5),
                         resetModem(6),
--   			being used in rel2.2(7)
--        		being used in rel2.2(8)
--         		reserve(9)
--         		reserve(10)
                         setCsuAuto(11),
                         upgradeComplete(12),
                         bootUpgrade(13),
			 softResetCoreDump(14)  -- reset with coredump
                     }
        MAX-ACCESS    read-write
        STATUS        current
        DESCRIPTION   "Initiate a system action."
        DEFVAL        { none }
        ::= { rcSystem 89 }

rcSysPowerUsage  OBJECT-TYPE
        SYNTAX              Integer32
        MAX-ACCESS   read-only
        STATUS             current
        DESCRIPTION "The current power usage for the whole chassis."
        ::= { rcSystem 90 }

rcSysPowerAvailable  OBJECT-TYPE
        SYNTAX              Integer32
        MAX-ACCESS   read-only
        STATUS             current
        DESCRIPTION "The current power available for the whole chassis."
        ::= { rcSystem 91 }

rcSysBpduStartMacAddress OBJECT-TYPE
        SYNTAX              MacAddress
        MAX-ACCESS   read-write
        STATUS             current
        DESCRIPTION "Starting Multicast MAC address for BPDUs"
        ::= { rcSystem 92 }

rcSysBpduMacAddressMask OBJECT-TYPE
        SYNTAX              Integer32 (1..48)
        MAX-ACCESS   read-write
        STATUS             current
        DESCRIPTION "BPDU MAC address Mask"
        ::= { rcSystem 93 }

rcSysFrcMsgControlTable OBJECT-TYPE
        SYNTAX        SEQUENCE OF RcSysFrcMsgControlEntry
        MAX-ACCESS    not-accessible
        STATUS        current
        DESCRIPTION   "Management Force-msg Control table. This table is used to 
                       specify the pattern for Force-msg Control"
        ::= { rcSystem 94 }
 
rcSysFrcMsgControlEntry OBJECT-TYPE
        SYNTAX        RcSysFrcMsgControlEntry
        MAX-ACCESS    not-accessible
        STATUS        current
        DESCRIPTION   "A  Force-msg Control table entry."
        INDEX         { rcSysFrcMsgControlPatternId }
        ::= { rcSysFrcMsgControlTable 1 }
 
RcSysFrcMsgControlEntry ::=
        SEQUENCE {
                rcSysFrcMsgControlPatternId Integer32,
                rcSysFrcMsgControlPattern DisplayString,
                rcSysFrcMsgControlRowStatus RowStatus    
        }
 
rcSysFrcMsgControlPatternId OBJECT-TYPE
        SYNTAX        Integer32 (1..32)
        MAX-ACCESS    not-accessible
        STATUS        current
        DESCRIPTION   "Pattern Id."
        ::= { rcSysFrcMsgControlEntry 1 }
     
         
rcSysFrcMsgControlPattern OBJECT-TYPE
        SYNTAX        DisplayString (SIZE (4))
        MAX-ACCESS    read-write
        STATUS        current
        DESCRIPTION   "Pattern for filtering the force-msg for msg control"
        ::= { rcSysFrcMsgControlEntry 2 }
         
rcSysFrcMsgControlRowStatus OBJECT-TYPE
        SYNTAX        RowStatus
        MAX-ACCESS    read-write
        STATUS        current
        DESCRIPTION   "Used to create/delete an entry"
        ::= { rcSysFrcMsgControlEntry 3 }

rcSysAccPolSnmpGrpTable OBJECT-TYPE 
        SYNTAX        SEQUENCE OF RcSysAccPolSnmpGrpEntry 
        MAX-ACCESS    not-accessible 
        STATUS        current 
        DESCRIPTION   "SNMP group list for access policy" 
        ::= { rcSystem 95 } 

rcSysAccPolSnmpGrpEntry OBJECT-TYPE 
        SYNTAX        RcSysAccPolSnmpGrpEntry 
        MAX-ACCESS    not-accessible 
        STATUS        current 
        DESCRIPTION   "The  table entry which covers the groups under snmp service." 
        INDEX         { rcSysAccessPolicyId, rcSysAccPolSnmpGrpName,                         rcSysAccPolSnmpGrpModel} 
        ::= { rcSysAccPolSnmpGrpTable 1 } 

RcSysAccPolSnmpGrpEntry ::= 
        SEQUENCE { 
                rcSysAccPolSnmpGrpName SnmpAdminString, 
                rcSysAccPolSnmpGrpModel SnmpSecurityModel, 
                rcSysAccPolSnmpGrpRowStatus RowStatus 
        } 

rcSysAccPolSnmpGrpName  OBJECT-TYPE 
        SYNTAX       SnmpAdminString
        MAX-ACCESS   not-accessible 
        STATUS       current 
        DESCRIPTION "The snmp-v3 group name" 
        ::= { rcSysAccPolSnmpGrpEntry 1 } 

rcSysAccPolSnmpGrpModel OBJECT-TYPE 
        SYNTAX       SnmpSecurityModel 
        MAX-ACCESS   not-accessible 
        STATUS       current 
        DESCRIPTION "The snmp model" 
        ::= { rcSysAccPolSnmpGrpEntry 2 } 

rcSysAccPolSnmpGrpRowStatus OBJECT-TYPE 
        SYNTAX       RowStatus 
        MAX-ACCESS   read-write 
        STATUS       current 
        DESCRIPTION "Row status" 
        ::= { rcSysAccPolSnmpGrpEntry 3 }

rcSysVirtualIpv6Addr OBJECT-TYPE
        SYNTAX        Ipv6Address
        MAX-ACCESS    read-write
        STATUS        current
        DESCRIPTION   "The virtual ipv6 address that is owned, advertised, and registered by the master CPU only.  Unlike the net management IP address this address is configured in the switch config file as opposed to the boot config."
        ::= { rcSystem 96 }

rcSysVirtualIpv6PrefixLength OBJECT-TYPE
        SYNTAX         Integer32 (0..128)
        MAX-ACCESS     read-write
        STATUS         current
        DESCRIPTION    "The length of the virtual ipv6 addr prefix (in bits)."
        ::= { rcSystem 97 }

rcSysConfigMode OBJECT-TYPE
        SYNTAX        INTEGER {
                               nncli(1),
                               cli(2)
                      }
        MAX-ACCESS    read-write
        STATUS        current
        DESCRIPTION   "This is used in conjunction with rcSysAction inorder
                      to decide the mode in which the config file is going to
                      be saved in."
        ::=  {rcSystem 98}

-- Extended PING Bypass 

rcSysExtendedPingBypass OBJECT IDENTIFIER ::= { rcSystem 99 }

rcSysExtendedPingBypassOUI OBJECT-TYPE
        SYNTAX        OCTET STRING (SIZE(0..3))
        MAX-ACCESS    read-write
        STATUS        current
        DESCRIPTION   "24-bit Organizationally Unique Idetifier.
		      Information on OUIs can be found in IEEE 802-2001
		      Clause 9."
        ::= { rcSysExtendedPingBypass 1 }

rcSysExtendedPingBypassMaxRate OBJECT-TYPE
        SYNTAX        Integer32 (1..10000)
        MAX-ACCESS    read-write
        STATUS        current
        DESCRIPTION   "Rate Limit in Mbps."
        DEFVAL        { 1 }
        ::= { rcSysExtendedPingBypass 2 }

rcSysExtendedPingBypassAdminState OBJECT-TYPE
        SYNTAX        EnableValue
        MAX-ACCESS    read-write
        STATUS        current
        DESCRIPTION   "Admin control for extended ping bypass."
        DEFVAL        { disable }
        ::= { rcSysExtendedPingBypass 3 }

rcSysExtendedPingBypassMatch OBJECT-TYPE
        SYNTAX        INTEGER {
                         src-mac(1),
                         dst-mac(2),
                         either(3),
                         both(4)
                      }
        MAX-ACCESS    read-write
        STATUS        current
        DESCRIPTION   "Bypass policer if the oui matches src-mac
		      or dst-mac or either or both."
        DEFVAL        { src-mac }
        ::= { rcSysExtendedPingBypass 4 }

-- Extended PING Bypass end

rcSysLicenseTrialDaysLeft OBJECT-TYPE
        SYNTAX        Unsigned32 (0..60)
        MAX-ACCESS    read-only
        STATUS        current
        DESCRIPTION   "This indicates days left before License Trial
                       Period will expire."
        ::= { rcSystem 100}

rcSysSingleMgmtIpAddr  OBJECT-TYPE
        SYNTAX        IpAddress
        MAX-ACCESS    read-write
        STATUS        current
        DESCRIPTION   "Single Managament IP Address "
        ::= { rcSystem 101 }

rcSysCopHighCpuUtilThreshold OBJECT-TYPE
        SYNTAX        Integer32 (60..100)
        MAX-ACCESS    read-write
        STATUS        current
        DESCRIPTION   "CopHighCpuUtilThreshold %"
        DEFVAL   { 100 }
        ::= { rcSystem 102 }

rcSysCopHighCpuUtilLogTime  OBJECT-TYPE
        SYNTAX        Integer32 (20..90)
        MAX-ACCESS    read-write
        STATUS        current
        DESCRIPTION   "rcSysCopHighCpuUtilLogTime in secs"
        DEFVAL   { 30 }
        ::= { rcSystem 103 }

rcSysConfigChangeFlag OBJECT-TYPE
        SYNTAX        TruthValue
        MAX-ACCESS    read-only
        STATUS        current
        DESCRIPTION   "Indicates whether the config file has been changed after loading of config"
        DEFVAL   { false }
        ::= { rcSystem 104 }  

rcSysBootUpgradeMode OBJECT-TYPE
       SYNTAX        INTEGER {
                        autoCommit(1),
                        manualCommit(2)
                     }
       MAX-ACCESS    read-write
       STATUS        current
       DESCRIPTION   "To set the mode of bootupgrade " 
       DEFVAL        { autoCommit }
       ::= { rcSystem 105 } 

rcSysBootUpgradeTime OBJECT-TYPE
        SYNTAX        Integer32 (0..60)
        MAX-ACCESS    read-write
        STATUS        current
        DESCRIPTION   "To set time for bootupgrade "
        DEFVAL        { 30 }
        ::= { rcSystem 106 }

rcSysBootUpgradeCsuMode OBJECT-TYPE
        SYNTAX        INTEGER {
                         none(1),
                         fullauto(2)
                      }
        MAX-ACCESS    read-write
        STATUS        current
        DESCRIPTION   "To set the mode of Csu for bootupgrade "
        DEFVAL        { none }
        ::= { rcSystem 107 } 

rcSysUpgradeStatus OBJECT-TYPE
        SYNTAX        INTEGER {
                         notInitiated(1),
                         complete(2),
                         inProgress(3),
                         failed(4)
                      }
        MAX-ACCESS    read-only
        STATUS        current
        DESCRIPTION   "To get the Upgrade status "
        DEFVAL        { notInitiated }
        ::= { rcSystem 108 } 

rcSysUpgradeCompleteStatus OBJECT-TYPE
        SYNTAX        INTEGER {
                         notRequired(1),
                         notConfirmed(2),
                         confirmed(3)
                      }
        MAX-ACCESS    read-only
        STATUS        current
        DESCRIPTION   "To get the Upgrade status"
        DEFVAL        { notRequired }
        ::= { rcSystem 109 } 

rcSysBootUpgradeConsistencyCheck OBJECT-TYPE
         SYNTAX          EnableValue
         MAX-ACCESS      read-write
         STATUS          current
         DESCRIPTION     "To enable or disable the consistency check in BootUpgrade"
         DEFVAL         { enable }
         ::= { rcSystem 110 }   

rcSysAutoSaveConfigState OBJECT-TYPE
         SYNTAX          EnableValue 
         MAX-ACCESS      read-write
         STATUS          current
         DESCRIPTION     "To enable or disable the autosaveconfig feature"
         DEFVAL          { disable }
         ::= { rcSystem 111}
rcSysAutoSaveConfigFileName OBJECT-TYPE
        SYNTAX      DisplayString (SIZE (0..255))
        MAX-ACCESS  read-write
        STATUS      current
        DESCRIPTION "The auto config file name in which the configurations have to be saved automatically."
        ::= { rcSystem 112 }

rcSysAutoSaveConfigInterval OBJECT-TYPE
        SYNTAX        Integer32 (15..75)
        MAX-ACCESS    read-write
        STATUS        current
        DESCRIPTION   "To set the Interval for autosave config"
        DEFVAL        { 30 }
        ::= { rcSystem 113 }

rcSysAutoSaveConfigChangeFlag OBJECT-TYPE
        SYNTAX        TruthValue
        MAX-ACCESS    read-only
        STATUS        current
        DESCRIPTION   "Indicates whether there are any configuration changes after last auto save config."
        DEFVAL   { false }
        ::= { rcSystem 114 }

rcSysAutoSaveConfigCounter OBJECT-TYPE
        SYNTAX        Integer32 (1..5)
        MAX-ACCESS    read-only
        STATUS        current
        DESCRIPTION   "Auto save config counter that should be prefixed to the filename."
        DEFVAL   { 1 }
        ::= { rcSystem 115 }

rcSysTotalPower OBJECT-TYPE
        SYNTAX        Integer32
        MAX-ACCESS    read-only
        STATUS        current
        DESCRIPTION   "The  total power for the whole chassis."
        ::= { rcSystem 116 }

rcSysRedundantPower OBJECT-TYPE
        SYNTAX        Integer32
        MAX-ACCESS    read-only
        STATUS        current
        DESCRIPTION   "Used to indicate the redundant power on the chassis.
		       The redundant power is per power supply unit"
        ::= { rcSystem 117 }

rcSysAuthSuccessTrapEnable OBJECT-TYPE
        SYNTAX        TruthValue
        MAX-ACCESS    read-write
        STATUS        current
        DESCRIPTION   "Used to enable/disable the trap send for authenticaion
			success trap rcnAuthenticationSuccess. It only allow
			to be set when snmpEnableAuthenTraps is enabled.
			I will be set to disable when snmpEnableAuthenTraps is
			disabled"
        ::= { rcSystem 118 }

rcSysUdpSrcByVirtualIpEnable OBJECT-TYPE
	SYNTAX	      TruthValue
	MAX-ACCESS    read-write
	STATUS        current
	DESCRIPTION   "Used to enable/disable virtual ip as udp source."
	DEFVAL	      { false }
	::= { rcSystem 119 }

--Software Release Info

rcSysSoftwareTable OBJECT-TYPE
        SYNTAX        SEQUENCE OF RcSysSoftwareEntry
        MAX-ACCESS    not-accessible
        STATUS        current
        DESCRIPTION   "A list of software releases added to the switch. Maximum
                       of 6 added releases can be present in the switch."
        ::= { rcSystem 120 }

rcSysSoftwareEntry OBJECT-TYPE
        SYNTAX        RcSysSoftwareEntry
        MAX-ACCESS    not-accessible
        STATUS        current
        DESCRIPTION   "Defines a row of rcSysSoftware Table using
                       RcSysSoftwareEntry Type."
        INDEX         { rcSysReleaseName }
        ::= { rcSysSoftwareTable 1 }

RcSysSoftwareEntry ::= SEQUENCE
              {
                rcSysReleaseName DisplayString,
                rcSysReleaseAddedTime DateAndTime,
                rcSysReleaseActivatedTime DateAndTime,
                rcSysReleaseCommittedTime DateAndTime,
                rcSysReleaseCommittedType INTEGER,
                rcSysReleaseType INTEGER
               }


rcSysReleaseName OBJECT-TYPE
        SYNTAX        DisplayString (SIZE (0..80))
        MAX-ACCESS    not-accessible
        STATUS        current
        DESCRIPTION   "Software Release Name"
        ::= { rcSysSoftwareEntry 1 }

rcSysReleaseAddedTime OBJECT-TYPE
        SYNTAX        DateAndTime
        MAX-ACCESS    read-only
        STATUS        current
        DESCRIPTION   "Software Release Added Date and Time"
        ::= { rcSysSoftwareEntry 2 }

rcSysReleaseActivatedTime OBJECT-TYPE
        SYNTAX        DateAndTime
        MAX-ACCESS    read-only
        STATUS        current
        DESCRIPTION   "Software Release Activated Date and Time"
        ::= { rcSysSoftwareEntry 3 }

rcSysReleaseCommittedTime OBJECT-TYPE
        SYNTAX        DateAndTime
        MAX-ACCESS    read-only
        STATUS        current
        DESCRIPTION   "Software Release Committed Date and Time"
        ::= { rcSysSoftwareEntry 4 }

rcSysReleaseCommittedType OBJECT-TYPE
        SYNTAX        INTEGER {
                         auto(1),       -- Release was auto-committed
                         manual(2),      -- Release was Manually committed
                         notCommitted(3),  --Release was not committed
                         none(4)        -- Details not available for this release
                      }

        MAX-ACCESS    read-only
        STATUS        current
        DESCRIPTION   "Software Release Committed Type"
        ::= { rcSysSoftwareEntry 5 }

rcSysReleaseType OBJECT-TYPE
        SYNTAX        INTEGER {
                         primary(1),  -- The Release is a primary release
                         backup(2),   -- The Release is a backup release
                         notUsed(3)   -- The Release is added but not being used
                      }

        MAX-ACCESS    read-only
        STATUS        current
        DESCRIPTION   "Software Release Type. This element tells whether the
                       release is a primary release for the switch or a backup
                       release or that the release has been added to the switch
                       but is not being used currently."
        ::= { rcSysSoftwareEntry 6 }

rcSysDataPathFaultShutdownEnable OBJECT-TYPE
    	SYNTAX		TruthValue
	MAX-ACCESS	read-write
	STATUS		current
	DESCRIPTION	"Used to enable/disable data path fault shutdown."
	DEFVAL 		{ true }
	::= { rcSystem 121 }

rcSysDnsServerIpv6Addr OBJECT-TYPE
        SYNTAX        Ipv6Address
        MAX-ACCESS    accessible-for-notify
        STATUS        current
        DESCRIPTION   "DNS server's IP address .  Used by trap rcnDNSv6RequestResponseTrap"
        ::= { rcSystem 122 }

rcSysReservedPower OBJECT-TYPE
    	SYNTAX        Integer32
        MAX-ACCESS    read-only
        STATUS        current
        DESCRIPTION   "Used to indicate the amount of power currently reserved 
	    	       on the system for critical cards that are present and 
		       other system critical modules such as cooling units."
        ::= { rcSystem 123 }

rcSysRequiredPower OBJECT-TYPE
    	SYNTAX        Integer32
        MAX-ACCESS    read-only
        STATUS        current
        DESCRIPTION   "Used to indicate the maximum amount of power required  
	    	       on the system for all reserved and any additional cards
		       that are present on the system to be powered on."
        ::= { rcSystem 124 }

rcSysLocatorLed OBJECT-TYPE
    	SYNTAX        INTEGER
                      {
                          off(1),    -- Switch the Locator LED to off
			  on(2)      -- Switch the Locator LED to on
                      }
        MAX-ACCESS    read-write
        STATUS        current
        DESCRIPTION   "Used to switch the locator LED on or off."
	DEFVAL	      { off }
        ::= { rcSystem 125 }

rcSysDefaultPingTracerouteContextType OBJECT-TYPE
    	SYNTAX        INTEGER {
		        grt(1),
			vrf(2),
			mgmt(3)
			}
        MAX-ACCESS    read-write
        STATUS        current
        DESCRIPTION   "The context execution type for a ping or traceroute."
	DEFVAL        { grt }
        ::= { rcSystem 126 }

rcSysDefaultPingTracerouteContextVrfName OBJECT-TYPE
    	SYNTAX        DisplayString(SIZE(0..64))
        MAX-ACCESS    read-write
        STATUS        current
        DESCRIPTION   "Vrf name associated with ping/traceroute context 
                       selection. Only valid if 
                       rcSystemDefaultPingTracerouteContextType equals vrf(2)."
        ::= { rcSystem 127 }

-- TFTP Upload/Download

rcTftpHost OBJECT-TYPE
        SYNTAX        IpAddress
        MAX-ACCESS    read-write
        STATUS        current
        DESCRIPTION   "Name of source/destination host for the TFTP
                      transfer."
        ::= { rcTftp 1 }

rcTftpFile OBJECT-TYPE
        SYNTAX      DisplayString (SIZE (0..255))
        MAX-ACCESS  read-write
        STATUS      current
        DESCRIPTION "Name of file for the TFTP transfer."
        ::= { rcTftp 2 }

rcTftpAction OBJECT-TYPE
        SYNTAX        INTEGER {
                          none(1),          -- none of the following
                          downloadConfig(2),
                          uploadConfig(3),
                          downloadSwToFlash(4),
                          downloadSwToPcmcia(5),
                          uploadSw(6),
                          downloadSwToDram(7)
                      }
        MAX-ACCESS	  read-write
        STATUS	      current
        DESCRIPTION   "The action for the TFTP transfer."
        DEFVAL        { none }
	::= { rcTftp 3 }

rcTftpResult OBJECT-TYPE
        SYNTAX        INTEGER {
                          none(1),
                          inProgress(2),
                          noResponse(3),
                          fileAccessError(4),
                          badFlash(5),
                          flashEraseFailed(6),
                          pcmciaEraseFailed(7),
                          success(8),
                          fail(9),
                          writeToNvramFailed(10),
                          flashWriteFailed(11),
                          pcmciaWriteFailed(12),
                          configFileTooBig(13),
                          imageFileTooBig(14),
                          noPcmciaDetect(15),
                          pcmciaNotSupported(16),
                          invalidFile(17),
                          noMemory(18),
                          xferError(19),
                          crcError(20),
                          readNvramFailed(21),
                          pcmciaWriteProtect(22)
	              }
        MAX-ACCESS    read-only
        STATUS        current
        DESCRIPTION   "Contains result of the last Tftp action request."
        ::= { rcTftp 4 }


-- PHYSICAL Elements

rcChasType OBJECT-TYPE
	SYNTAX	      INTEGER {
		         unknown(1),   -- unknown chassis
 		         a1100(2),     -- 3  slot chassis (1/2, 1/2, full)
 		         a1250(6),     -- 4  slot chassis (full, ... , full)
 		         a1150(7),     -- 3  slot chassis (1/2, 1/2, full)
 		         a1200(8),     -- 8  slot chassis (full, ... , full)
 			 a1050(9),            -- 2  slot chassis (seahawk)
 			 a8006(280887558),    -- 6  slot chassis (raptillion)
       			 a8010(280887562),    -- 10 slot chassis (raptillion)
       			 a8010co(1623064842), -- 10 slot Central Office Chassis
                         a8003(280887555),    -- 3  slot chassis (raptillion)
                         a1612G(1086197761),  --  1 slot 12 port cobra (0x40be1001)
                         a1624G(1086201857),  --  1 slot 24 port cobra (0x40be2001)
                         a1648T(1086210049),  -- 1 slot 52 port cobra (0x40be4001)
                         a8306(1354629382),   -- 6  slot 8300 POE chassis (0x50be0106)
                         a8310(1354629386),   -- 10 slot 8300 POE chassis (0x50be010a)
                         a8011co(1623064843), -- 11 slot Central Office chassis (tripod)
			 a8003r(280891651),   -- 3 clot chassis MERS-8003-R (Triumph)
-- Cobalt Blue
			 -- Avaya Order#:	NTC201CA
			 -- Customer Order#:	EC1402001
			 a9012(1090388736), -- 0100 0000 1111 1110 0000 0011 0000 0000 0x40FE0300
			 a9010(1090388737), -- 0100 0000 1111 1110 0000 0011 0000 0001 0x40FE0301
	              -- VSP4K 			 
			 a4850GTS(1232273458), -- 0100 1001 0111 0011 0000 0000 0011 0010 0x49730032
	   		 a4850GTSPWRPLUS(1232277554),    -- 0100 1001 0111 0011 0001 0000 0011 0010 0x49731032 
                         a4450GSXPWRPLUS(1231228978),    -- 0100 1001 0110 0011 0001 0000 0011 0010 0x49631032
			 a4450GSX(1231224882),               -- 0100 1001 0110 0011 0000 0000 0011 0010 0x49630032
			 a4450GTXHTPWRPLUS(1232279602),  -- 0100 1001 0111 0011 0001 1000 0011 0010 0x49731832
			 a8284XSQ(1331822677),      -- 0100 1111 0110 0010 0000 0000 0101 0101 0x4f620055
			 a8404(1331823105),         -- 0100 1111 0110 0010 0000 0010 0000 0001 0x4f620201
			 a8404C(1331839489),        -- 0100 1111 0110 0010 0100 0010 0000 0001 0x4f624201
			 a8608(1425195264),         -- 0101 0100 1111 0010 1100 0001 0000 0000 (0x54f2c100)  
			 a7254XSQ(1331855415),      -- 0100 1111 0110 0010 1000 0000 0011 0111 0x4f628037
			 a7254XTQ(1332903991),      -- 0100 1111 0111 0010 1000 0000 0011 0111 0x4f728037
-- APLS
			 aDSG6248(1232274482),      -- 0100 1001 0111 0011 0000 0100 0011 0010  (0x49730432)
			 aDSG6248P(1232278578),     -- 0100 1001 0111 0011 0001 0100 0011 0010  (0x49731432)
			 aDSG6248CFP(1231230002),   -- 0100 1001 0110 0011 0001 0100 0011 0010 (0x49631432)
			 aDSG7648(1331856439),      -- 0100 1111 0110 0010 1000 0100 0011 0111 (0x4f628437)
			 aDSG7648C(1332905015),     -- 0100 1111 0111 0010 1000 0100 0011 0111 (0x4f728437) 
			 aDSG7480(1331823701),      -- 0100 1111 0110 0010 0000 0100 0101 0101 (0x4f620455)
			 aDSG8032(929170433),        -- 0011 0111 0110 0010 0000 0100 0000 0001 (0x37620401)	

-- ES6100:
                         a7432CQ(1332042530),    -- 0100 1111 0110 0101 0101 1011 0010 0010  (0x4f655b22) Display: VSP7432CQ
			 a7456VSC(1332042554),   -- 0100 1111 0110 0101 0101 1011 0011 1010  (0x4f655b3a) Display: VSP7456VSC
	                 a1104(1008861208),          -- 0011 1100 0010 0010 0000 0000 0001 1000 (0x3c220018)          			 
                         a4624GTSPWRPLUS(2065862680), -- 0111 1011 0010 0010 1001 0000 0001 1000  (0x7B229018) (24 x 10/100/1000Mb Poe COPPER)
                         a4648GTSPWRPLUS(2065862704)  -- 0111 1011 0010 0010 1001 0000 0011 0000  (2065862704) (48 x 10/100/1000Mb Poe COPPER)

			 
	              }
	MAX-ACCESS 	  read-only
	STATUS 	      current
	DESCRIPTION   "Chassis Type"
        ::= { rcChassis 1 }

rcChasSerialNumber OBJECT-TYPE
        SYNTAX        DisplayString (SIZE (0..16))
        MAX-ACCESS    read-only
        STATUS        current
        DESCRIPTION   "Unique serial number for this chassis."
        ::= { rcChassis 2 }

rcChasHardwareRevision OBJECT-TYPE
	SYNTAX 	      DisplayString (SIZE (0..20))
	MAX-ACCESS 	  read-only
	STATUS 	      current
	DESCRIPTION   "Device hardware revision level"
	::= { rcChassis 3 }
	
rcChasNumSlots OBJECT-TYPE
        SYNTAX        Integer32 (1..16)
        MAX-ACCESS    read-only
        STATUS        current
        DESCRIPTION   "The number of slots in the chassis available for
                      plug-in cards."
        ::= { rcChassis 4 }

rcChasNumPorts OBJECT-TYPE
        SYNTAX        Integer32 (0..255) 
        MAX-ACCESS    read-only
        STATUS        current
        DESCRIPTION   "The total number of ports currently installed in
		      the chassis."
        ::= { rcChassis 5 }

-- TBD FIXME : We need to get the final list from Hardware
rcChasTestResult OBJECT-TYPE
	SYNTAX        INTEGER {
			 other(1),
			 ok(2),
			 crceeprom(3),
			 timer(4),
			 procdram(5),
			 led(6),
       	         	 formaccpuaccess(7),
       	         	 asiccpuaccess(8),
                	 memory(9),
                	 loopback(10)
		      }
	MAX-ACCESS 	  read-only
	STATUS 	      current
	DESCRIPTION   "Chassis start-up diagnostic tests."
	::= { rcChassis 6 }

rcChasFan OBJECT IDENTIFIER ::= { rcChassis 7 }

rcChasFanTable OBJECT-TYPE
	SYNTAX        SEQUENCE OF RcChasFanEntry
	MAX-ACCESS    not-accessible
	STATUS        current
	DESCRIPTION   "This table contains information about Fans"
	::= { rcChasFan 1 }

rcChasFanEntry OBJECT-TYPE
	SYNTAX        RcChasFanEntry
	MAX-ACCESS    not-accessible
	STATUS        current
	DESCRIPTION   "Contains information regarding a Fan Unit"
	INDEX         { rcChasFanId }
	::= { rcChasFanTable 1 }

RcChasFanEntry ::=
	SEQUENCE {
		rcChasFanId Integer32,
		rcChasFanOperStatus INTEGER,
		rcChasFanAmbientTemperature Gauge32,
                rcChasFanType INTEGER,
 	        rcChasFanFlowType INTEGER
	}

rcChasFanId OBJECT-TYPE
	SYNTAX        Integer32 (1..6)
	MAX-ACCESS    read-only
	STATUS        current
	DESCRIPTION   "The chassis fan Id."
	::= { rcChasFanEntry 1 }

rcChasFanOperStatus OBJECT-TYPE
	SYNTAX        INTEGER {
		         unknown(1),
		         up(2),
		         down(3),
			 notpresent(4)
	              }
	MAX-ACCESS    read-only
	STATUS        current
	DESCRIPTION   "Actual status of the Fan:
	              - unknown(1) - status can not be determined.
	              - up(2) - present and supplying power.
	              - down(3) - present, but failure indicated.
		      - notpresent(4) -- not present"
	::= { rcChasFanEntry 2 }

rcChasFanAmbientTemperature OBJECT-TYPE
        SYNTAX          Gauge32
        MAX-ACCESS      read-only
        STATUS          current
        DESCRIPTION     "Used to indicate the temperature of the air
                        entering the fan."
        ::= { rcChasFanEntry 3 }

rcChasFanType OBJECT-TYPE
        SYNTAX        INTEGER {
                         unknown(1),
                         regularSpeed(2),
                         highSpeed(3)
                      }
        MAX-ACCESS    read-only
        STATUS        current
        DESCRIPTION   "Type of the Fan:
                      - unknown(1) - type can not be determined.
                      - regularSpeed(2) - regular speed fan is present.
                      - highSpeed(3) - high speed fan is present."
        ::= { rcChasFanEntry 4 }
    
rcChasFanFlowType OBJECT-TYPE
        SYNTAX        INTEGER {
                         unknown(1),
                         frontToBack(2),
                         backToFront(3)
                      }
        MAX-ACCESS    read-only
        STATUS        current 
        DESCRIPTION   "Direction of the Fan Flow:
                      - unknown(1) - Flow can not be determined.
                      - fronttoback(2) - Front to back flow.
                      - backtofront(3) - Back to front flow."
        ::= { rcChasFanEntry 5 }
    
rcChasFanZoneTable OBJECT-TYPE
     SYNTAX SEQUENCE OF RcChasFanZoneEntry
     MAX-ACCESS   not-accessible
     STATUS       current
     DESCRIPTION  "Table for the zones available on the chassis"
     ::= { rcChasFan 2 }

rcChasFanZoneEntry OBJECT-TYPE
     SYNTAX        RcChasFanZoneEntry
     MAX-ACCESS    not-accessible
     STATUS        current
     DESCRIPTION   "Contains information regarding a zone unit"
     INDEX        { rcChasFanZoneType }
     ::= { rcChasFanZoneTable 1 }

RcChasFanZoneEntry ::=
     SEQUENCE {
           rcChasFanZoneType INTEGER,
           rcChasFanZoneMode INTEGER,
           rcChasFanZoneModeStatus BITS,
           rcChasFanZoneAlarmTimer  Integer32,
           rcChasFanZoneTemperature Gauge32,
           rcChasFanZoneTray1LedColor INTEGER,
           rcChasFanZoneTray2LedColor INTEGER,
	   rcChasFanZoneFPGATemperature Integer32,
	   rcChasFanZoneFATemperature   Integer32
     }

rcChasFanZoneType OBJECT-TYPE
     SYNTAX INTEGER {
                 front(1),
                 rear(2)
            }
     MAX-ACCESS   not-accessible
     STATUS       current
     DESCRIPTION  "Type of the fan zone."
     ::= { rcChasFanZoneEntry 1 }

rcChasFanZoneMode OBJECT-TYPE
     SYNTAX INTEGER {
                 normal(1),
                 alarm(2)
            }
     MAX-ACCESS   read-only
     STATUS       current
     DESCRIPTION  "Functional mode of the fan zone."
     ::= { rcChasFanZoneEntry 2 }

rcChasFanZoneModeStatus OBJECT-TYPE
     SYNTAX  BITS {
                 normal(0),
                 fanFault(1),
                 alarmThresholdExceeded(2)
            }
     MAX-ACCESS   read-only
     STATUS       current
     DESCRIPTION  "Bit set indicates the alarm type(s)"
     ::= { rcChasFanZoneEntry 3 }

rcChasFanZoneAlarmTimer OBJECT-TYPE
     SYNTAX       Integer32
     UNITS        "seconds"
     MAX-ACCESS   read-only
     STATUS       current
     
     DESCRIPTION  "Alarm timer indicates the remaining time before 
                   system checks and shutdown module when fan is in
		   the alarm state. Zero means the fan i snot in an
                   alarm state"
     ::= { rcChasFanZoneEntry 4 }

rcChasFanZoneTemperature OBJECT-TYPE
     SYNTAX       Gauge32
     MAX-ACCESS   read-only
     STATUS       current
     DESCRIPTION  "Highest temperature measured in celsius degree
		   from all the sensors (inlet and outlet) in the zone"
     ::= { rcChasFanZoneEntry 5 }

rcChasFanZoneTray1LedColor OBJECT-TYPE
     SYNTAX       INTEGER {
                     off(1),
                     green(2),
                     red(3),
                     amber(4)
		  }
     MAX-ACCESS   read-only
     STATUS       current
     DESCRIPTION  "Led color indicate fans operation status on tray
                   off:   Indicates no tray or power off.
                   green: Indicates all fans are operational in a tray.
		   red:   Front Zone Tray: more than one fans in a tray are not opertional.
                          Rear Zone Tray: one of two or both fans fans in a tray are not operational.
                   amber: Front Zone Tray: one of eight fans is not operational.
                           Rear Zone Tray: It is not applicable for Rear Zone tray"
			
     ::= { rcChasFanZoneEntry 6 }

 rcChasFanZoneTray2LedColor OBJECT-TYPE
     SYNTAX       INTEGER {
                     off(1),
		     green(2),
                     red(3),
                     amber(4)
		  }
     MAX-ACCESS   read-only
     STATUS       current
     DESCRIPTION  "Led color indicate fans operation status on tray
		   off:   Indicates no tray or power off.
                   green: Indicates all fans are operational in a tray.
		   red:   Front Zone Tray: more than one fans in a tray are not opertional.
                          Rear Zone Tray: one of two fans or both fans in a tray are not operational.
                   amber: Front Zone Tray: one of eight fans is not operational.
                           Rear Zone Tray: It is not applicable for Rear Zone tray"
     ::= { rcChasFanZoneEntry 7 }

rcChasFanZoneFPGATemperature OBJECT-TYPE
     SYNTAX       Integer32
     UNITS        "celsius"
     MAX-ACCESS   read-only
     STATUS       current
     DESCRIPTION  "Highest FPGA temperature measured in celsius degree
		   from all the FPGA sensors in the zone. FPGA sensors
		   are only available on the RoF cards. Hence this is 
		   applicable only for the front zone. 
		   A value of 0 for this mib object indicates that this
		   is not applicable."
     ::= { rcChasFanZoneEntry 8 }

rcChasFanZoneFATemperature OBJECT-TYPE
     SYNTAX       Integer32
     UNITS        "celsius"
     MAX-ACCESS   read-only
     STATUS       current
     DESCRIPTION  "Highest FA temperature measured in celsius degree
		   from all the FA sensors in the zone. FA sensors
		   are only available on the RoF cards. Hence this is 
		   applicable only for the front zone. 
		   A value of 0 for this mib object indicates that this
		   is not applicable."
     ::= { rcChasFanZoneEntry 9 }

rcChasFanInfoTable OBJECT-TYPE
     SYNTAX        SEQUENCE OF RcChasFanInfoEntry
     MAX-ACCESS    not-accessible
     STATUS        current
     DESCRIPTION   "This table contains information for 
                    all the fans on the chassis"
     ::= { rcChasFan 3 }

rcChasFanInfoEntry OBJECT-TYPE
     SYNTAX        RcChasFanInfoEntry
     MAX-ACCESS    not-accessible
     STATUS        current
     DESCRIPTION   "Contains information regarding a fan unit"
     INDEX        { rcChasFanZoneType, rcChasFanInfoTray, rcChasFanInfoFan }
     ::= { rcChasFanInfoTable 1 }

RcChasFanInfoEntry ::=
     SEQUENCE {
           rcChasFanInfoTray INTEGER,
           rcChasFanInfoFan INTEGER,
           rcChasFanInfoExpectedSpeed INTEGER,
           rcChasFanInfoOperSpeed INTEGER,
           rcChasFanInfoStatus INTEGER
     }

rcChasFanInfoTray OBJECT-TYPE
     SYNTAX INTEGER (1..2)
     MAX-ACCESS   not-accessible 
     STATUS       current
     DESCRIPTION  "Number of trays per zone in chassis"
     ::= { rcChasFanInfoEntry 1 }

rcChasFanInfoFan OBJECT-TYPE
     SYNTAX INTEGER (1..8)
     MAX-ACCESS   not-accessible
     STATUS       current
     DESCRIPTION  "Number of fans per tray"
     ::= { rcChasFanInfoEntry 2 }

rcChasFanInfoExpectedSpeed OBJECT-TYPE
     SYNTAX INTEGER {
                 low(1),
                 medium(2),
                 high(3),
                 hardware(4)
            }
     MAX-ACCESS   read-only
     STATUS       current
     DESCRIPTION  "The administrative setting for the fan speed
                   low:       Low speed set by software
                   medium:    Medium speed set by software
                   high:      High speed set by software
                   hardware:  Speed controlled by hardware"
     ::= { rcChasFanInfoEntry 3 }

rcChasFanInfoOperSpeed OBJECT-TYPE
     SYNTAX INTEGER {
                 low(1),
                 medium(2),
                 high(3),
                 hardware(4),
                 error(5)
            }
     MAX-ACCESS   read-only
     STATUS       current
     DESCRIPTION  "Actual speed of the fan"
     ::= { rcChasFanInfoEntry 4 }

rcChasFanInfoStatus OBJECT-TYPE
     SYNTAX INTEGER {
                 ok(1),
                 faulty(2)
            }
     MAX-ACCESS   read-only
     STATUS       current
     DESCRIPTION  "The operational status of the fan. Details below:
                   ok(1):       Fan operating under normal condition(s)
                   faulty(2):   Fan not operating as expected"
     ::= { rcChasFanInfoEntry 5 }

rcChasPowerSupply OBJECT IDENTIFIER ::= { rcChassis 8 }

rcChasPowerSupplyTable OBJECT-TYPE
	SYNTAX        	SEQUENCE OF RcChasPowerSupplyEntry
	MAX-ACCESS        	not-accessible
	STATUS        	current
	DESCRIPTION   	"This table contains information about power 
		      	supplies."
	::= { rcChasPowerSupply 1 }

rcChasPowerSupplyEntry OBJECT-TYPE
	SYNTAX        	RcChasPowerSupplyEntry
	MAX-ACCESS        	not-accessible
	STATUS        	current
	DESCRIPTION   	"Contains information regarding a power supply
		      	unit."
	INDEX  { rcChasPowerSupplyId }
	::= { rcChasPowerSupplyTable 1 }

RcChasPowerSupplyEntry ::=
	SEQUENCE {
		rcChasPowerSupplyId Integer32,
		rcChasPowerSupplyOperStatus INTEGER
	}

rcChasPowerSupplyId OBJECT-TYPE
	SYNTAX        	Integer32 (1..8)
	MAX-ACCESS      read-only
	STATUS        	current
	DESCRIPTION    "The power supply Id.
	    		Sapphire Chassis has 8 power supplies."
	::= { rcChasPowerSupplyEntry 1 }


rcChasPowerSupplyOperStatus OBJECT-TYPE
	SYNTAX         INTEGER {
		          unknown(1),
		          empty(2),
		          up(3),
	     	          down(4)
	               }
	MAX-ACCESS     read-only
	STATUS         current
	DESCRIPTION   "Actual status of the power supply:
	              - unknown(1) - status can not be determined.
	              - empty(2) - power supply not installed.
	              - up(3) - present and supplying power.
	              - down(4) - present, but failure indicated."
	::= { rcChasPowerSupplyEntry 2 }


rcChasPowerSupplyDetailTable OBJECT-TYPE
	SYNTAX        	SEQUENCE OF RcChasPowerSupplyDetailEntry
	MAX-ACCESS        	not-accessible
	STATUS        	current
	DESCRIPTION   	"This table contains detailed information about
    	                 power supplies."
	::= { rcChasPowerSupply 2 }

rcChasPowerSupplyDetailEntry OBJECT-TYPE
	SYNTAX        	RcChasPowerSupplyDetailEntry
	MAX-ACCESS        	not-accessible
	STATUS        	current
	DESCRIPTION   	"Contains detailed info regarding a power supply
		      	unit."
	INDEX  { rcChasPowerSupplyDetailId }
	::= { rcChasPowerSupplyDetailTable 1 }

RcChasPowerSupplyDetailEntry ::=
	SEQUENCE {
		rcChasPowerSupplyDetailId            Integer32,
		rcChasPowerSupplyDetailType          INTEGER,
		rcChasPowerSupplyDetailSerialNumber  DisplayString,
		rcChasPowerSupplyDetailHardwareRevision DisplayString,
		rcChasPowerSupplyDetailPartNumber    DisplayString,
		rcChasPowerSupplyDetailDescription   DisplayString,
		rcChasPowerSupplyDetailPsePower      Integer32,
		rcChasPowerSupplyDetailInputLineVoltage INTEGER,
		rcChasPowerSupplyDetailOperLineVoltage INTEGER,
		rcChasPowerSupplyDetailOutputWatts   Integer32,
		rcChasPowerSupplyDetailDualAcInput   INTEGER,
		rcChasPowerSupplyFanFlowType         INTEGER,
		rcChasPowerSupplyDetailInputOperLineVoltage Integer32,
                rcChasPowerSupplyDetailInputPower           Integer32
 

	}

rcChasPowerSupplyDetailId OBJECT-TYPE
      SYNTAX   	  Integer32 (1..6)
      MAX-ACCESS   	  read-only
      STATUS   	  current
      DESCRIPTION "The power supply Id."
      ::= { rcChasPowerSupplyDetailEntry 1 }

rcChasPowerSupplyDetailType OBJECT-TYPE
      SYNTAX   	   INTEGER {
                       unknown(0),
                       ac(1),
                       dc(2),
		       dualAc(3),
                       poe(278798592) , -- 8300 110/200 V AC/DC PoE(0x109e2100)
	  poe1400WPS(278802688), -- 8300 110/200 V 850W/1400W AC/DC PoE(0x109e3100)   
                      dc8005(277876736) -- 8005 1462W 48/60V DC Power Supply(0x10901000)
                   }
      MAX-ACCESS   	   read-only
      STATUS   	   current
      DESCRIPTION  "The power supply type."
      ::= { rcChasPowerSupplyDetailEntry 2 }

rcChasPowerSupplyDetailSerialNumber OBJECT-TYPE
      SYNTAX      DisplayString (SIZE (0..16))
      MAX-ACCESS  read-only
      STATUS      current
      DESCRIPTION "The power supply serial number."
      ::= { rcChasPowerSupplyDetailEntry 3 }

rcChasPowerSupplyDetailHardwareRevision OBJECT-TYPE
      SYNTAX      DisplayString (SIZE (0..16))
      MAX-ACCESS  read-only
      STATUS      current
      DESCRIPTION "The hardware revision of the power supply."
      ::= { rcChasPowerSupplyDetailEntry 4 }

rcChasPowerSupplyDetailPartNumber OBJECT-TYPE
      SYNTAX      DisplayString (SIZE (0..16))
      MAX-ACCESS  read-only
      STATUS      current
      DESCRIPTION "The power supply part number."
      ::= { rcChasPowerSupplyDetailEntry 5 }

rcChasPowerSupplyDetailDescription OBJECT-TYPE
      SYNTAX      DisplayString (SIZE (0..64))
      MAX-ACCESS  read-only
      STATUS      current
      DESCRIPTION "The detail description of power supply."
      ::= { rcChasPowerSupplyDetailEntry 6 }

rcChasPowerSupplyDetailPsePower OBJECT-TYPE
        SYNTAX        Integer32 (1..65535)
        MAX-ACCESS    read-only
        STATUS        current
        DESCRIPTION   "The nominal power of the PSE expressed in Watts."
        ::= { rcChasPowerSupplyDetailEntry 7 }

rcChasPowerSupplyDetailInputLineVoltage OBJECT-TYPE
      SYNTAX      INTEGER {
                       unknown(0),
                       low110v(1),
                       high220v(2),
		       minus48v(3),
		       ac110vOr220v(4),
		       dc(5)
                  }
      MAX-ACCESS  read-only
      STATUS      current
      DESCRIPTION "The power supply Input Line voltage."
      ::= { rcChasPowerSupplyDetailEntry 8 }

rcChasPowerSupplyDetailOperLineVoltage OBJECT-TYPE
      SYNTAX      INTEGER {
                       unknown(0),
                       low110v(1),
                       high220v(2),
		       minus48v(3),
		       ac110vOr220v(4),
		       dc(5)
                  }
      MAX-ACCESS  read-only
      STATUS      current
      DESCRIPTION "The power supply Line voltage considered for
                   Power Management calculation."
      ::= { rcChasPowerSupplyDetailEntry 9 }

rcChasPowerSupplyDetailOutputWatts OBJECT-TYPE
      SYNTAX      Integer32
      MAX-ACCESS   read-only
      STATUS       current
      DESCRIPTION  "The output power of this power supply"
      ::= { rcChasPowerSupplyDetailEntry 10 }

rcChasPowerSupplyDetailDualAcInput OBJECT-TYPE
      SYNTAX       INTEGER {
                       line1(1),
                       line2(2),
                       both(3),
		       none(4),
		       notApplicable(5)
                   }
      MAX-ACCESS   read-only
      STATUS       current
      DESCRIPTION  "The dual input power supply has two input AC lines.
	  	    This mib object defines which of those AC lines are 
		    supplying power. For a single input power supply the
		    value will be set to notApplicable(5)."
      DEFVAL	   { 5 }
      ::= { rcChasPowerSupplyDetailEntry 11 }

rcChasPowerSupplyFanFlowType    OBJECT-TYPE
      SYNTAX      INTEGER {
                       frontToback(1),
                       backTofront(2),
                       unknown(3)
                   }
      MAX-ACCESS   read-only
      STATUS       current
      DESCRIPTION  "The power supply Fan Flow Type."
      ::= { rcChasPowerSupplyDetailEntry 12 }
  
rcChasPowerSupplyDetailInputOperLineVoltage OBJECT-TYPE
      SYNTAX       Integer32
      MAX-ACCESS   read-only
      STATUS       current
      DESCRIPTION  "The actual power supply input line voltage."
      ::= { rcChasPowerSupplyDetailEntry 13 }

rcChasPowerSupplyDetailInputPower OBJECT-TYPE
      SYNTAX       Integer32
      MAX-ACCESS   read-only
      STATUS       current
      DESCRIPTION  "The input power of this power supply."
      ::= { rcChasPowerSupplyDetailEntry 14 }

  
rcCard OBJECT IDENTIFIER ::= { rcChassis 9 }

rcCardTable OBJECT-TYPE
	SYNTAX        SEQUENCE OF RcCardEntry
	MAX-ACCESS    not-accessible
	STATUS        current
	DESCRIPTION   "A table that contains information about the 
                      cards in this chassis.  For those slots that 
                      do not contain a physical card, the table may 
		      be implemented to contain a conceptual row 
                      with the type of physical module set to 
 		      'chasCardEmpty', or it may be implemented to 
		      have no conceptual row instance."
	::= { rcCard 1 }

rcCardEntry OBJECT-TYPE
	SYNTAX        RcCardEntry
	MAX-ACCESS    not-accessible
	STATUS        current
	DESCRIPTION   "Card attributes"
	INDEX         { rcCardIndex }
	::= { rcCardTable 1 }

RcCardEntry ::=
	SEQUENCE {
		rcCardIndex Integer32,
		rcCardType INTEGER,
		rcCardSerialNumber DisplayString,
		rcCardHardwareRevision DisplayString,
		rcCardAdminStatus INTEGER,
		rcCardOperStatus INTEGER,
		rcCardPCMCIAType INTEGER,
		rcCardPartNumber DisplayString,
		rcCardOxateCpld DisplayString,
		rcCardOxideFpga DisplayString,
		rcCardCatskillFpga DisplayString,
		rcCardQE DisplayString,
		rcCardK2Fpga DisplayString,
		rcCardIoDateDC DisplayString,
		rcCardIoDateBB DisplayString,
		rcCardIoPimCpld DisplayString,
		rcCardLed0Cpld DisplayString,
		rcCardLed1Cpld DisplayString,
		rcCardZagrosFpga DisplayString,
		rcCardRsp DisplayString,
		rcCardBcmMac DisplayString,
		rcCardPhosphideFpga DisplayString,
		rcCardSulfideFpga DisplayString,
		rcCardFluorateCpld DisplayString,
 		rcCardBme DisplayString
	}

rcCardIndex OBJECT-TYPE
        SYNTAX        	Integer32 (1..26)
        MAX-ACCESS        	read-only
        STATUS       	current
        DESCRIPTION   	"A unique value for each module within the chassis.
                      	This value is determined by the chassis slot number
                      	where the module is inserted.  Valid entries are 1
                      	to the value of rcChasNumSlots"
        ::= { rcCardEntry 1 }

rcCardType OBJECT-TYPE
        SYNTAX INTEGER 
	{
	other(1),                        -- no card installed
        rcCPU(2),                        -- [1200] CPU Card (A1200)
        rc8x100BaseTX(3),                -- [1208TX] 8 port (cat 5) (A1200)
        rc8x100BaseT2(4),                -- [] 8 port (cat 3) (A1200)
        rc8x100BaseF(5),                 -- [1208FX] 8 port fiber (A1200)
        rc16x100BaseTX(6),               -- [1216TX] 16 port (cat 5) (A1200)
        rc8x100BaseTXWG(12),             -- [1108TX] 8 port (half width) (A1100)
        rc16x100BaseTXWG(13),            -- [1100] 16 port + CPU (A1100)
        rc4x100BaseFWG(14),              -- [1104FX] 4 port (half width) (A1100)
        rc12x100BaseTXWG(15),            -- [1050] 12 port + CPU (A1050)
        rc12x100BaseFBB(16),             -- [] 12 port (A1200)
        rc8x100BaseFWG(17),              -- [1108FX] 8 port (A1100)
        rc12x100BaseTX-2x100BaseFBB(18), -- [] 12 port + 2 port (A1200)
        rc2x155BaseFBB(19),              -- [] 2 sonet port (A1200)
        rc4x155BaseFBB(20),              -- [] 4 sonet port (A1200)
        rc16x100BaseFBB(21),             -- [1216FX] 16 port fiber (A1200)
        rc14x100BaseTX-2x100BaseFBB(22), -- [1216TF] 14 port + 2 port (A1200)
        rc8x10BaseFBB(23),               -- [1208FL] 8 port fiber low-speed (A1200)
	rc4xOC3(24),			 -- [1200xx] 4 port OC3 (A1200)
	rc1xOC12(25),			 -- [1200xx] 1 port OC12 (A1200)
        rcRMON(26),			 -- [1200xx] RMON (A1200) 
        rc1xOC12POSBaseMMF(27),          -- [1200xx] 1 port OC12 POS (A1200)
        rc1xOC12POSBaseSMF(28),          -- [1200xx] 1 port OC12 POS (A1200)
        rc4x1000BaseSXWG(1028),          -- [1150] 1 0 00 000 0100 + CPU (A1150)
        rc1x1000BaseSXWG(1025),          -- [1101SX] 1 0 00 000 0001
        rc2x1000BaseSXWG(1026),          -- [1102SX] 1 0 00 000 0010
        rc1x1000BaseSXRWG(1537),         -- [1101SR] 1 1 00 000 0001
        rc2x1000BaseSXRWG(1538),         -- [1102SR] 1 1 00 000 0010
        rc1x1000BaseLXWG(1153),          -- [1101LX] 1 0 01 000 0001
        rc2x1000BaseLXWG(1154),          -- [1102LX] 1 0 01 000 0010
        rc2x1000BaseXDWG(1282),          -- [1102XD] 1 0 10 000 0010
        rc1x1000BaseLXRWG(1665),         -- [1101LR] 1 1 01 000 0001
        rc2x1000BaseLXRWG(1666),         -- [1102LR] 1 1 01 000 0010
        rc1x1000BaseSXBB(1041),          -- [1201SX] 1 0 00 001 0001
        rc2x1000BaseSXBB(1042),          -- [1202SX] 1 0 00 001 0010
        rc1x1000BaseSXRBB(1553),         -- [1201SR] 1 1 00 001 0001
        rc2x1000BaseSXRBB(1554),         -- [1202SR] 1 1 00 001 0010
        rc1x1000BaseLXBB(1169),          -- [1201LX] 1 0 01 001 0001
        rc2x1000BaseLXBB(1170),          -- [1202LX] 1 0 01 001 0010
        rc2x1000BaseXDBB(1298),          -- [1202XD] 1 0 10 001 0010
        rc1x1000BaseLXRBB(1681),         -- [1201LR] 1 1 01 001 0001
        rc2x1000BaseLXRBB(1682),         -- [1202LR] 1 1 01 001 0010
-- Cobalt Blue
        cbMidplane-28(1090388736) ,      -- 0100 0000 1111 1110 0000 0011 0000 0000 0x40FE0300
        cbMidplaneSapphire(1090396928),  -- 0100 0000 1111 1110 0010 0011 0000 0000 0x40FE2300
	cbACPowerSupply(1084097280),     -- 0100 0000 1001 1110 0000 0011 0000 0000 0x409E0300
        cbACPowerPlusSupply(1084130048), -- 0100 0000 1001 1110 1000 0110 0000 0000 0x409E8300	    
	cbCPFanTray(1085145856),         -- 0100 0000 1010 1110 0000 0011 0000 0000 0x40AE0300
        cbIOFanTray(1085149952),         -- 0100 0000 1001 1110 0000 0011 0000 0000 0x40AE1300
        cbFanTray(1085154048),           -- 0100 0000 1010 1110 0010 0011 0000 0000 0x40AE2300
	cbHSFanTray(1085158144),         -- 0100 0000 1010 1110 0011 0011 0000 0000 0x40AE3300	    
	cbAUX(1091437312),               -- 0100 0001 0000 1110 0000 0011 0000 0000 0x410E0300
        cbSF3200(1075708672),            -- 0100 0000 0001 1110 0000 0011 0000 0000 0x401E0300
        cbSF9600(1075712768),            -- 0100 0000 0001 1110 0001 0011 0000 0000 0x401E1300
	cbSF9610(1075716864),            -- 0100 0000 0001 1110 0010 0011 0000 0000 0x401E2300
	cbCP-CSC(1073873665),            -- 0100 0000 0000 0010 0000 0011 0000 0001 0x40020301
        cb48x1000BaseTX(1075970864),     -- 0100 0000 0010 0010 0000 0011 0011 0000 0x40220330
        cb48x1000BaseTXPOE(1075974960),  -- 0100 0000 0010 0010 0001 0011 0011 0000 0x40221330
        cb48x1000SFP(1077044016),        -- 0100 0000 0011 0010 0110 0011 0011 0000 0x40326330
        cb24x10GBaseSFP(1077109528),     -- 0100 0000 0011 0011 0110 0011 0001 1000 0x40336318
        cb48x10GBaseSFP(1077109552),     -- 0100 0000 0011 0011 0110 0011 0011 0000 0x40336330
-- Future CB Cards
        --  cbOPM(1087243008)           0x40CE0300
        --  cbSAS(1087247104)           0x40CE1300  
        --  cbIPFIX(1087251200)         0x40CE2300
-- CB generation 2 (ROF) linecards
        rof48x1000SFP(1144152880),           -- 0100 0100 0011 0010 0110 0011 0011 0000 0x44326330
        rofLoadBoard(1144152832),            -- 0100 0100 0011 0010 0110 0011 0000 0000 0x44326300
        rof16x10GBaseSFP(1144218384),        -- 0100 0100 0011 0011 0110 0011 0001 0000 0x44336310
        rof48x10GBaseSFP(1144218416),        -- 0100 0100 0011 0011 0110 0011 0011 0000 0x44336330
        rof4x40GBaseSFP(1144283920),       	 -- 0100 0100 0011 0100 0110 0011 0001 0000 0x44346310
 	rof12x40GBaseSFP(1144283952),      	 -- 0100 0100 0011 0100 0110 0011 0011 0000 0x44346330
-- VSP4K card definitions
	vsp4k4850GTS(1232273458),       -- 0100 1001 0111 0011 0000 0000 0011 0010 0x49730032
	vsp4k4850GTSPWRPLUS(1232277554),    -- 0100 1001 0111 0011 0001 0000 0011 0010 0x49731032
	vsp4k4450GSXPWRPLUS(1231228978),     -- 0100 1001 0110 0011 0001 0000 0011 0010 0x49631032
	vsp4k4450GSX(1231224882),            -- 0100 1001 0110 0011 0000 0000 0011 0010 0x49630032 
	vsp4k4450GTXHTPWRPLUS(1232279602),   -- 0100 1001 0111 0011 0001 1000 0011 0010 0x49731832
	vsp8k8242XSQ(1298407466)             -- 0100 1101 0110 0100 0010 0000 0010 1010 0x4d64202a
	}
	MAX-ACCESS 	      	read-only
	STATUS 	      	current
	DESCRIPTION   	"Used to indicate a card types in the Accelar
			1000 product families.  

			For Accelar 1000 devices, gigabit cards use
		      	an encoded value according to the following rule:

                                +-----+--+-+---+---+---+
                      	bits  : |31-11|10|9|8-7|6-4|3-0|
                                +-----+--+-+---+---+---+
                      	field : |  a  | b|c| d | e | f |
                                +-----+--+-+---+---+---+

                             a : not-used
                             b : 1=gigabit
                             c : 0=non-redundant, 
                                 1=redundant
                             d : 0=short-haul, 
                                 1=long-haul, 
                                 2=extra-distance,
                             e : 0=work-group(a1100 and a1150)
                                 1=back-bone(a1200, f1250, and f2000), 
                             f : 1=1-port, 2=2-port, 4=4-port, 8=8-port
                      "
	::= { rcCardEntry 2 }

rcCardSerialNumber OBJECT-TYPE
        SYNTAX        DisplayString (SIZE (0..16))
	MAX-ACCESS    read-only
	STATUS        current
	DESCRIPTION   "Unique serial number for this card."
	::= { rcCardEntry 3 }

rcCardHardwareRevision OBJECT-TYPE
	SYNTAX        DisplayString (SIZE (0..8))
	MAX-ACCESS    read-only
	STATUS        current
	DESCRIPTION   "Hardware Version"
	::= { rcCardEntry 4 }

rcCardAdminStatus OBJECT-TYPE
        SYNTAX       INTEGER { 
			 up(1),
         		 down(2),
			 testing(3)
                      }
        MAX-ACCESS    read-write 
        STATUS        current
        DESCRIPTION   "Used to indicate the administrative status of this
                       card"
        ::= { rcCardEntry 5 }

rcCardOperStatus OBJECT-TYPE
	SYNTAX        INTEGER { 
			 up(1),
         		 down(2),
			 testing(3),
			 unknown(4),
		 	 dormant(5)
                      }
	MAX-ACCESS    read-only
	STATUS        current
	DESCRIPTION   "Used to indicate the operational status of this card."
	::= { rcCardEntry 6 }

rcCardPCMCIAType OBJECT-TYPE
        SYNTAX        INTEGER {
			 none(1),
			 modem28kbs(2),
			 flash2meg(3),
			 flash4meg(4)
                      }
        MAX-ACCESS    read-only
        STATUS        current
        DESCRIPTION   "Used to indicate the type of PCMCIA card currently
                      installed in this CPU card, if any.

                      For non-CPU cards, this variable has no meaning and
                      will always be set to none."
	DEFVAL        { none }
        ::= { rcCardEntry 7 }

rcCardPartNumber OBJECT-TYPE
        SYNTAX        	DisplayString (SIZE (0..16))
        MAX-ACCESS        	read-only
        STATUS        	current
        DESCRIPTION   	"Card Part Number"
        ::= { rcCardEntry 8 }

rcCardOxateCpld OBJECT-TYPE
        SYNTAX        DisplayString (SIZE (0..8))
        MAX-ACCESS    read-only
        STATUS        current 
        DESCRIPTION   "Oxate CPLD version for CP card"
        ::= { rcCardEntry 9 }

rcCardOxideFpga OBJECT-TYPE
        SYNTAX        DisplayString (SIZE (0..8)) 
        MAX-ACCESS    read-only
        STATUS        current
        DESCRIPTION   "Oxide FGPA version for CP card"
        ::= { rcCardEntry 10 }

rcCardCatskillFpga OBJECT-TYPE
        SYNTAX        DisplayString (SIZE (0..8))
        MAX-ACCESS    read-only
        STATUS        current
        DESCRIPTION   "Catskill FPGA version for CP card"
        ::= { rcCardEntry 11 }

rcCardQE OBJECT-TYPE
        SYNTAX        DisplayString (SIZE (0..8))
        MAX-ACCESS    read-only
        STATUS        current
        DESCRIPTION   "QE version for CP card"
        ::= { rcCardEntry 12 }

rcCardK2Fpga OBJECT-TYPE
        SYNTAX        DisplayString (SIZE (0..8))
        MAX-ACCESS    read-only
        STATUS        current
        DESCRIPTION   "K2 FPGA version for IO card"
        ::= { rcCardEntry 13 }

rcCardIoDateDC OBJECT-TYPE
        SYNTAX        DisplayString (SIZE (0..8))
        MAX-ACCESS    read-only
        STATUS        current
        DESCRIPTION   "IO Date DC CPLD for IO card"
        ::= { rcCardEntry 14 }

rcCardIoDateBB OBJECT-TYPE
        SYNTAX        DisplayString (SIZE (0..8))
        MAX-ACCESS    read-only
        STATUS        current
        DESCRIPTION   "IO Date BaseBoard CPLD for IO card"
        ::= { rcCardEntry 15 } 

rcCardIoPimCpld OBJECT-TYPE
        SYNTAX        DisplayString (SIZE (0..8))
        MAX-ACCESS    read-only
        STATUS        current
        DESCRIPTION   "IO PIM CPLD for IO card"
        ::= { rcCardEntry 16 }

rcCardLed0Cpld OBJECT-TYPE
        SYNTAX        DisplayString (SIZE (0..8))
        MAX-ACCESS    read-only
        STATUS        current
        DESCRIPTION   "LED0 CPLD for IO card"
        ::= { rcCardEntry 17 }

rcCardLed1Cpld OBJECT-TYPE
        SYNTAX        DisplayString (SIZE (0..8))
        MAX-ACCESS    read-only
        STATUS        current
        DESCRIPTION   "LED1 CPLD for IO card"
        ::= { rcCardEntry 18 }

rcCardZagrosFpga OBJECT-TYPE
        SYNTAX        DisplayString (SIZE (0..8))
        MAX-ACCESS    read-only
        STATUS        current
        DESCRIPTION   "Zagros FPGA for IO card"
        ::= { rcCardEntry 19 }

rcCardRsp OBJECT-TYPE
        SYNTAX        DisplayString (SIZE (0..8))
        MAX-ACCESS    read-only
        STATUS        current
        DESCRIPTION   "RSP for IO card" 
        ::= { rcCardEntry 20 }

rcCardBcmMac OBJECT-TYPE
        SYNTAX        DisplayString (SIZE (0..8))
        MAX-ACCESS    read-only
        STATUS        current
        DESCRIPTION   "BCM Mac for IO card"
        ::= { rcCardEntry 21 }

rcCardPhosphideFpga OBJECT-TYPE
        SYNTAX        DisplayString (SIZE (0..8))
        MAX-ACCESS    read-only
        STATUS        current
        DESCRIPTION   "Phosphide FPGA for IO card"
        ::= { rcCardEntry 22 }

rcCardSulfideFpga OBJECT-TYPE
        SYNTAX        DisplayString (SIZE (0..8))
        MAX-ACCESS    read-only
        STATUS        current
        DESCRIPTION   "Sulfide FPGA for IO card"
        ::= { rcCardEntry 23 }

rcCardFluorateCpld OBJECT-TYPE
        SYNTAX        DisplayString (SIZE (0..8))
        MAX-ACCESS    read-only
        STATUS        current
        DESCRIPTION   "Fluorate Cpld for SF card"
        ::= { rcCardEntry 24 }

rcCardBme OBJECT-TYPE
        SYNTAX        DisplayString (SIZE (0..8))
        MAX-ACCESS    read-only
        STATUS        current
        DESCRIPTION   "BME for SF card"
        ::= { rcCardEntry 25 }  

rcPort OBJECT IDENTIFIER ::= { rcChassis 10 } -- defined in rcPortXXX.mib

-- Additional Chassis Group Variables

rcChasAruMode OBJECT-TYPE
        SYNTAX        	INTEGER 
			{
				aruOne(1),
				aruTwo(2),
				aruThree(3)
			}
        MAX-ACCESS        	read-only
        STATUS        	current
        DESCRIPTION   	"The ARU mode the chassis is operating in."
        ::= { rcChassis 12 }

rcChasQuidMode OBJECT-TYPE
        SYNTAX        	INTEGER 
			{
				quidMixed(1),
				quidTwo(2),
				quidThree(3),
				quidFour(4),
				quidFive(5)
			}
        MAX-ACCESS        	read-only
        STATUS        	current
        DESCRIPTION   	"The Quid mode the chassis is operating in."
        ::= { rcChassis 13 }

rcChasEocModeAdminStatus OBJECT-TYPE
        SYNTAX        	INTEGER 
			{
				default(0),
				aru1Quid4(1),
				aru2Quid4(2),
				aru2Quid5(3),
				aru3Quid4(4),
				aru3Quid5(5)
			}
        MAX-ACCESS        	read-write
        STATUS        	current
        DESCRIPTION     "Used to specify the Enforce Operational
                        Configuration Mode(EOC) of the system.  When a
                        device is configured with hardware of different
                        revisions, the system will initialize in some
                        deterministic manner (e.g., the lowest common
                        denominator that makes sense based on the hardware
                        configuration).  This is the 'default(0)' mode.
                        The user can override this behavior by manually
                        specifying the EOC Mode they would like."
        ::= { rcChassis 14 }
    
rcChasPartNumber OBJECT-TYPE
	SYNTAX      DisplayString (SIZE (0..16))
	MAX-ACCESS    read-only
	STATUS 	      current
	DESCRIPTION   "Device part number or PEC code "
	::= { rcChassis 66 }
	
rcChasModelName OBJECT-TYPE
	SYNTAX      DisplayString (SIZE (0..32))
	MAX-ACCESS    read-only
	STATUS 	      current
	DESCRIPTION   "Chassis model name. For APLS platform, The model name
	               which is in the SEEPROM"
	::= { rcChassis 67 }
    
rcChasBrandName OBJECT-TYPE
	SYNTAX      DisplayString (SIZE (0..32))
	MAX-ACCESS    read-only
	STATUS 	      current
	DESCRIPTION   "Brand name (company name). For APLS platform,
	               The brand name which is programmed in SEEPROM"
	::= { rcChassis 68 }    
-- Agent Table
 
rcAgentTable OBJECT-TYPE
        SYNTAX        SEQUENCE OF RcAgentEntry
        MAX-ACCESS    not-accessible
        STATUS        current
        DESCRIPTION   "Agents in a chassis table"
        ::= { rcChassis 16 }
 
rcAgentEntry OBJECT-TYPE
        SYNTAX        RcAgentEntry
        MAX-ACCESS    not-accessible
        STATUS        current
        DESCRIPTION   "Entry containing info. for a particular agent"
        INDEX         { rcAgentId }
        ::= { rcAgentTable 1 }
 
RcAgentEntry ::= SEQUENCE {
                rcAgentId       Integer32,
                rcAgentSlot     Integer32,
                rcAgentIpAddr   IpAddress
        }
 
rcAgentId OBJECT-TYPE
        SYNTAX        Integer32 (0..2147483647)
        MAX-ACCESS    read-only
        STATUS        current
        DESCRIPTION   "entry id"
        ::= { rcAgentEntry 1 }
 
rcAgentSlot OBJECT-TYPE
        SYNTAX        Integer32
        MAX-ACCESS    read-only
        STATUS        current
        DESCRIPTION   "slot agent is in."
        ::= { rcAgentEntry 2 }
 
rcAgentIpAddr OBJECT-TYPE
         SYNTAX        IpAddress
         MAX-ACCESS    read-only
         STATUS        current
         DESCRIPTION   "agent's ip address."
         ::= { rcAgentEntry 3 }

rcChasEocModeOperStatus OBJECT-TYPE
        SYNTAX        	INTEGER 
			{
				default(0),
				aru1Quid4(1),
				aru2Quid4(2),
				aru2Quid5(3),
				aru3Quid4(4),
				aru3Quid5(5)
			}
        MAX-ACCESS        	read-only
        STATUS        	current
        DESCRIPTION     "Used to indicate the Enforce Operational
                        Configuration Mode(EOC) of the system."
        ::= { rcChassis 15 }

rcChasBrouterPorts OBJECT-TYPE
        SYNTAX        	PortSet 
        MAX-ACCESS        	read-only
        STATUS        	current
        DESCRIPTION   	"Used to indicate which ports in the system are
			configured as Brouter ports."
        ::= { rcChassis 17 }

rcChasGlobalFilterEnable OBJECT-TYPE
        SYNTAX        	TruthValue 
        MAX-ACCESS        	read-write
        STATUS        	current
        DESCRIPTION   	"Used to enable/disable global filters in the
			system.  This variable is currently not supported."
	DEFVAL		{ false }
        ::= { rcChassis 18 }

rcChasVlanBySrcMacEnable OBJECT-TYPE
        SYNTAX        	TruthValue 
        MAX-ACCESS        	read-write
        STATUS        	current
        DESCRIPTION   	"Used to enable/disable source MAC based VLANs
			in the system."
	DEFVAL		{ false }
        ::= { rcChassis 19 }

rcChasDiffServEcnCompatibilityEnable OBJECT-TYPE
        SYNTAX          TruthValue
        MAX-ACCESS      read-write
        STATUS          current
        DESCRIPTION     "Used to enable/disable the Explicit Congestion
                        Notification(ECN) compatibility feature.
                        When set to FALSE , the system will mask the ECN bits
                        in the DS field while re-marking DSCP and will not match
                        on ECN capable flows if filter is set on DSmatch.
                        When set to TRUE, it will preserve the ECN bits in the DS
                        field while re-marking and will match on full 8-bit DS field."
        DEFVAL          { false }
        ::= { rcChassis 20 }


rcChasNewEnhancedOperMode OBJECT-TYPE
        SYNTAX        TruthValue  
        MAX-ACCESS    read-write
        STATUS        current
        DESCRIPTION   "Enhanced operational mode."
        ::= { rcChassis 21 } 

rcChasNewEMMode OBJECT-TYPE
        SYNTAX        TruthValue
        MAX-ACCESS    read-write
        STATUS        current
        DESCRIPTION   "This configuration is for enabling/disabling 128K
                       mode.  The change will take effect upon reboot."
        ::= { rcChassis 22 }

rcChasEmModeError OBJECT-TYPE
        SYNTAX       INTEGER {
                         none(1),
                         non128KCardOffLine(2),
                         checkSlaveConfigNResetForEmMMode(3),
                         mismatchResetForEmMode(4),
                         mismatchEmModeMasterSlave(5),
                         incompatMasterResetForEmMode(6),
                         putSlaveOffEmImcompat(7),
                         slave8690EmIncompatGoingOffline(8),
                         cpu8690DisableEm(9)
                      }
        MAX-ACCESS    read-only
        STATUS        current
        DESCRIPTION   "Used to indicate the Em-mode error status"
        ::= { rcChassis 23 }

rcChasEnhancedOperMode OBJECT-TYPE
        SYNTAX        TruthValue
        MAX-ACCESS    read-only
        STATUS        current
        DESCRIPTION   "Enhanced Operational mode the switch currently has 
                       booted and will remain the same unitl the next reboot."
        ::= { rcChassis 24 }

rcChasEMMode OBJECT-TYPE
        SYNTAX        TruthValue
        MAX-ACCESS    read-only
        STATUS        current
        DESCRIPTION   "EM mode the switch currently has booted and 
                       will remain the same unitl the next reboot."
        ::= { rcChassis 25 }
 
rcChasFtpDaemonInSecondaryCpu OBJECT-TYPE
        SYNTAX          TruthValue
        MAX-ACCESS      read-write
        STATUS          current
        DESCRIPTION     "Used to enable/disable FTP daemon in 2nd cpu."
               DEFVAL           { false }
        ::= { rcChassis 26 }

rcChasSmltOnSingleCpEnable OBJECT-TYPE
        SYNTAX        TruthValue
        MAX-ACCESS    read-write
        STATUS        current
        DESCRIPTION   "Enable SMLT on single CP feature in the switch"
        ::= { rcChassis 27 }

rcChasNewVlanOptmMode OBJECT-TYPE
        SYNTAX        TruthValue
        MAX-ACCESS    read-write
        STATUS        current
        DESCRIPTION   "Vlan Optimization mode."
        ::= { rcChassis 28 }   
 
rcChasVlanOptmMode OBJECT-TYPE
        SYNTAX        TruthValue
        MAX-ACCESS    read-only
        STATUS        current
        DESCRIPTION   "Vlan Optimization mode the switch currently has
                       booted and will remain the same unitl the next 
                       reboot."
        ::= { rcChassis 29 }  

-- defined in rcLaunchPadXXX.mib
rcLaunchPad OBJECT IDENTIFIER ::= { rcChassis 30 }
rcChasNaapEnable OBJECT-TYPE
        SYNTAX        EnableValue
        MAX-ACCESS    read-write
        STATUS        current
        DESCRIPTION   "To enable/disbale to napp feature."
        ::= { rcChassis 31 }

rcChasGlobalFilterOrderingEnable OBJECT-TYPE
        SYNTAX        TruthValue
        MAX-ACCESS    read-write
        STATUS        current
        DESCRIPTION   "Used to enable/disable global filter ordering
                       in the system."
        DEFVAL        { false }
        ::= { rcChassis 32 }

rcChasNewGlobalFilterOrderingEnable OBJECT-TYPE
        SYNTAX        TruthValue
        MAX-ACCESS    read-write
        STATUS        current
        DESCRIPTION   "This configuration is for enabling/disabling
                       global filter ordering. The change will take
                       effect upon reboot."
        DEFVAL        { false }
        ::= { rcChassis 33 }  

rcChasWsmDirectMode OBJECT-TYPE
        SYNTAX        TruthValue
        MAX-ACCESS    read-write
        STATUS        current
        DESCRIPTION   "This is for enabling/disabling configuration of same 
	              community strings on the WSM and 8600.  This if for 
		      allowing users to connect directly via SNMP to the WSM 
		      blade."           
        DEFVAL        { false }
        ::= { rcChassis 34 }

rcChasRspMode OBJECT-TYPE
        SYNTAX        TruthValue
        MAX-ACCESS    read-write
        STATUS        current
        DESCRIPTION   "This configuration is for enabling/disabling 256K
                       mode. The change will take effect upon reboot."
        ::= { rcChassis 35 }

rcChasRspOperMode OBJECT-TYPE
        SYNTAX        TruthValue
        MAX-ACCESS    read-only
        STATUS        current
        DESCRIPTION   "R-mode the switch currently has booted and 
                       will remain the same until the next reboot."
        ::= { rcChassis 36 }

rcChasRspModeError OBJECT-TYPE
        SYNTAX       INTEGER {
                         none(1),
                         non256KCardOffLine(2)
                      }
        MAX-ACCESS    read-only
        STATUS        current
        DESCRIPTION   "Used to indicate the r-mode error status"
        ::= { rcChassis 37 }

rcChasPOE OBJECT IDENTIFIER ::=  { rcChassis 38 }

rcChasPOEPower OBJECT-TYPE
        SYNTAX          Integer32
        MAX-ACCESS      read-only
        STATUS          current
        DESCRIPTION     "The total PoE power which this chassis 
                         supports (Unit in Watts)."
        ::= { rcChasPOE 1 }

rcChasPOEAllocatedPower OBJECT-TYPE
        SYNTAX          Integer32
        MAX-ACCESS      read-only
        STATUS          current
        DESCRIPTION     "The total PoE power allocated for PoE modules
                         installed in this chassis (Unit in Watts)."
        ::= { rcChasPOE 2 }

rcChasPOEAvailablePower OBJECT-TYPE
        SYNTAX          Integer32
        MAX-ACCESS      read-only
        STATUS          current
        DESCRIPTION     "The total PoE power available for any
                         additional PoE power request or allocation
                         (Unit in Watts)."
        ::= { rcChasPOE 3 }

rcChasPOEBackUpPower OBJECT-TYPE
        SYNTAX          Integer32
        MAX-ACCESS      read-only
        STATUS          current
        DESCRIPTION     "The total PoE power reserved for backup or
                         redundancy (Unit in Watts)."
        ::= { rcChasPOE 4 }

-- rcRepeater 

rcRepeater OBJECT IDENTIFIER ::= { rcChassis 39 }

rcRepeaterTable OBJECT-TYPE
        SYNTAX        SEQUENCE OF RcRepeaterEntry
        MAX-ACCESS    not-accessible
        STATUS        current
        DESCRIPTION   "Port repeater table"
        ::= { rcRepeater 1 }

rcRepeaterEntry OBJECT-TYPE
        SYNTAX        RcRepeaterEntry
        MAX-ACCESS    not-accessible
        STATUS        current
        DESCRIPTION   "Entry containing info. for a particular repeater"
        INDEX         { rcRepeaterId }
        ::= { rcRepeaterTable 1 }

RcRepeaterEntry ::= SEQUENCE {
    	rcRepeaterId          	 Integer32,
    	rcRepeaterFirstPort      InterfaceIndex,
	rcRepeaterSecondPort     InterfaceIndex,
	rcRepeaterVlanId         Integer32,
	rcRepeaterName           DisplayString,              
	rcRepeaterRowStatus      RowStatus
    	}

rcRepeaterId OBJECT-TYPE
        SYNTAX        Integer32 (1..32)	 
        MAX-ACCESS    read-only	
        STATUS        current
        DESCRIPTION   "A value that uniquely identifies the repeater."
        ::= { rcRepeaterEntry 1 }

rcRepeaterFirstPort OBJECT-TYPE
        SYNTAX        InterfaceIndex
        MAX-ACCESS    read-write
        STATUS        current
        DESCRIPTION   "First port member of the Repeater"
        ::= { rcRepeaterEntry 2 }

rcRepeaterSecondPort OBJECT-TYPE
        SYNTAX        InterfaceIndex
        MAX-ACCESS    read-write
        STATUS        current
        DESCRIPTION   "Second port member of the Repeater"
        ::= { rcRepeaterEntry 3 }	

rcRepeaterVlanId OBJECT-TYPE
        SYNTAX        Integer32 (0..4094)
        MAX-ACCESS    read-write
        STATUS        current
        DESCRIPTION   "A value that uniquely identifies the Virtual LAN 
                      associated with first port"
        ::= { rcRepeaterEntry 4 }

rcRepeaterName OBJECT-TYPE
        SYNTAX        DisplayString (SIZE (0..20))
        MAX-ACCESS    read-write
        STATUS        current
        DESCRIPTION   "An administratively-assigned name for this repeater."
        ::= { rcRepeaterEntry 5 }

rcRepeaterRowStatus OBJECT-TYPE
        SYNTAX        RowStatus
        MAX-ACCESS    read-write
        STATUS        current
        DESCRIPTION   "Used to create/delete entries in the rcRepeater."
        ::= { rcRepeaterEntry 6 }

rcChasMcastCheckPktEnable OBJECT-TYPE
        SYNTAX        TruthValue
        MAX-ACCESS    read-write
        STATUS        current
        DESCRIPTION   "Used to enable/disable Multicast check packet in the
            	       system. This change will take effect upon reboot. "
        DEFVAL           { true }
        ::= { rcChassis 40 }

rcChasSystemMonitorEnable OBJECT-TYPE 
        SYNTAX        TruthValue 
        MAX-ACCESS    read-write 
        STATUS        current 
        DESCRIPTION   "Enable/Disable System monitoring in the switch" 
        DEFVAL        { true } 
        ::= { rcChassis 41 } 

rcChasSysMonMonitoringEnable OBJECT-TYPE 
        SYNTAX          TruthValue 
        MAX-ACCESS      read-write 
        STATUS          current 
        DESCRIPTION     "Dyanamically Enable/Disable SystemMonitor monitoring 
                         engine in the switch" 
        DEFVAL          { true } 
        ::= { rcChassis 42 } 

rcChasSysMonDetectionTime OBJECT-TYPE 
        SYNTAX        Integer32 (10..600) 
        MAX-ACCESS    read-write 
        STATUS        current 
        DESCRIPTION   "System Monitor Detection time in seconds" 
	DEFVAL	      { 30 }
        ::= { rcChassis 43 } 

rcChasNewMulticastResourceReservation OBJECT-TYPE
        SYNTAX        Integer32 (64..4083)
        MAX-ACCESS    read-write
        STATUS        current
        DESCRIPTION   "Used to reserve MGIDs for IP Multicast.
                      The change will take effect upon reboot."
        DEFVAL        { 2048 }
        ::= { rcChassis 44 }

rcChasMulticastResourceReservation OBJECT-TYPE
        SYNTAX        Integer32 (64..4083)
        MAX-ACCESS    read-only
        STATUS        current
        DESCRIPTION   "MGIDs the switch currently has reserved for IP       
                      Multicast; will remain the same until the next
                      reboot."
        ::= { rcChassis 45 }

rcChasNewMaxVlanResourceReservation OBJECT-TYPE
        SYNTAX        EnableValue
        MAX-ACCESS    read-write
        STATUS        current
        DESCRIPTION   "A mode where all MGIDs are reserved for VLAN use
                      only; no IPMC.  The change will take effect upon
                      reboot."
        DEFVAL        { disable }
        ::= { rcChassis 46 }
       
rcChasMaxVlanResourceReservation OBJECT-TYPE
        SYNTAX        EnableValue
        MAX-ACCESS    read-only
        STATUS        current
        DESCRIPTION   "Tells if all MGIDs are reserved for VLAN use.  Will
                      remain the same until the next reboot."
        ::= { rcChassis 47 }

rcChasMgidUsageVlanCurrent OBJECT-TYPE
        SYNTAX        Integer32 (1..4084)
        MAX-ACCESS    read-only
        STATUS        current
        DESCRIPTION   "Number of MGIDs currently used for VLAN, including
                      SMLT"
        ::= { rcChassis 48 }

rcChasMgidUsageVlanRemaining OBJECT-TYPE
        SYNTAX        Integer32 (0..4084)
        MAX-ACCESS    read-only
        STATUS        current
        DESCRIPTION   "Number of MGIDs remaining allocated for VLAN"
        ::= { rcChassis 49 }

rcChasMgidUsageMulticastCurrent OBJECT-TYPE
        SYNTAX        Integer32 (0..4083)
        MAX-ACCESS    read-only
        STATUS        current
        DESCRIPTION   "Number of MGIDs currently used for IPMC"
        ::= { rcChassis 50 }

rcChasMgidUsageMulticastRemaining OBJECT-TYPE
        SYNTAX        Integer32 (0..4083)
        MAX-ACCESS    read-only
        STATUS        current
        DESCRIPTION   "Number of MGIDs remaining allocated for IPMC"
        ::= { rcChassis 51 }

rcChasPowerManagementEnable OBJECT-TYPE
     SYNTAX        TruthValue
     MAX-ACCESS     read-write
     STATUS     current
     DESCRIPTION     "Turn on or off Chassis Power Management. The
                      configuration will take effect upon reboot"
     DEFVAL     { true }
     ::= { rcChassis 52 }

rcChasForceTopologyIpFlagEnable OBJECT-TYPE
        SYNTAX          TruthValue
        MAX-ACCESS      read-write
        STATUS          current
        DESCRIPTION     "Used to enable/disable flag which is used to
                         set the CLIP-ip as topology ip"
        DEFVAL          { false }
        ::= { rcChassis 53 }
 
rcChasCircuitlessIpId OBJECT-TYPE
        SYNTAX          Integer32(1..256)
        MAX-ACCESS      read-write
        STATUS          current
        DESCRIPTION     "The Clip-Id set by the user to be used as Topology-ip"
        ::= { rcChassis 54 }

rcChasPowerManagementOriginalEnable OBJECT-TYPE
        SYNTAX        TruthValue
        MAX-ACCESS    read-only
        STATUS        current
        DESCRIPTION   "On or off value of Chassis Power Management which the
                       switch has currently booted. It will remain the same
                       until the next reboot."
        DEFVAL        { true }
        ::= { rcChassis 55 }

rcChasPowerManagementFanCheck OBJECT-TYPE
        SYNTAX        TruthValue
        MAX-ACCESS    read-write
        STATUS        current
        DESCRIPTION   "Turn on or off the Fan Check functionility of Chassis
                       Power Management. The value takes effect only on reboot."
        DEFVAL        { true }
        ::= { rcChassis 56 }
 
rcChasPowerManagementFanCheckOriginalState OBJECT-TYPE
        SYNTAX        TruthValue
        MAX-ACCESS    read-only
        STATUS        current
        DESCRIPTION   "The on or off value of fan check which the switch has
                       booted with. The value does not take effect till the next
                       reboot."
        DEFVAL        { true }
        ::= { rcChassis 57 }

rcChasEsmHashIndex OBJECT-TYPE
        SYNTAX        TruthValue
        MAX-ACCESS    read-write
        STATUS        current
        DESCRIPTION   "This is for enabling/disabling hashing on the upper 24 bits of the UNI for ESM card"
        DEFVAL        { false }
        ::= { rcChassis 58 }

rcChasSwitchFabricRedundancy OBJECT-TYPE
        SYNTAX        EnableValue
        MAX-ACCESS    read-write
        STATUS        current
        DESCRIPTION   "Turn on or off 2:1 Redundancy for 8011co Chassis"
        DEFVAL        { enable }
        ::= { rcChassis 59 }

rcChasSystemDefault OBJECT-TYPE
        SYNTAX          TruthValue
        MAX-ACCESS      read-write
        STATUS          current
        DESCRIPTION     "Used to default the system"
	DEFVAL          { false }
        ::= { rcChassis 60 }

rcChasTakeIOCardOfflineEnable OBJECT-TYPE
        SYNTAX        TruthValue
        MAX-ACCESS    read-write
        STATUS        current
        DESCRIPTION   "Enable/Disable IO Card to go offline when 
		       F2E sees excessive resets. 
		       This change will take effect upon reboot."
        DEFVAL           { false }
        ::= { rcChassis 61 }

rcChasAutoResetFabricEnable OBJECT-TYPE
        SYNTAX        TruthValue
        MAX-ACCESS    read-write
        STATUS        current
        DESCRIPTION   "Enable/Disable fabric to be reset automatically 
		       on fab mem full error.
		       This change will take effect upon reboot."
        DEFVAL           { false }
        ::= { rcChassis 62 }

rcChasSecurityConsoleFlag  OBJECT-TYPE
	SYNTAX          TruthValue
        MAX-ACCESS      read-write
        STATUS          current
        DESCRIPTION     "Used to enable/disable flag which is used for 
	                 Security Console.When it is enabled, the console 
			 connection works only with the null modem cable"
	DEFVAL          { true }
        ::= { rcChassis 63 }

rcChasRcBridgeFdbOldQueryFlagEnable OBJECT-TYPE
        SYNTAX          TruthValue
        MAX-ACCESS      read-write
        STATUS          current
        DESCRIPTION     "Used to enable/disable rcBridgeNewFdbTable for 
                         fdb query " 
        DEFVAL          { false }
        ::= { rcChassis 64 }

rcChasLed OBJECT IDENTIFIER ::= { rcChassis 65 }

rcChasLedTable OBJECT-TYPE
	SYNTAX        SEQUENCE OF RcChasLedEntry
	MAX-ACCESS    not-accessible
	STATUS        current 
	DESCRIPTION   "This table contains information about LEDs of the chassis"
	::= { rcChasLed 1 }

rcChasLedEntry OBJECT-TYPE
	SYNTAX        RcChasLedEntry
	MAX-ACCESS    not-accessible
	STATUS        current 
	DESCRIPTION   "Contains information regarding a LED Unit"
	INDEX         { rcChasLedId }
	::= { rcChasLedTable 1 }

RcChasLedEntry ::=
	SEQUENCE {
		rcChasLedId            INTEGER,
		rcChasLedLabel         DisplayString (SIZE (0..15)),
		rcChasLedStatus        INTEGER
	}

rcChasLedId OBJECT-TYPE
	SYNTAX        INTEGER(1..6)
	MAX-ACCESS    read-only
	STATUS        current 
	DESCRIPTION   "The chassis LED Id."
	::= { rcChasLedEntry 1 }

rcChasLedLabel OBJECT-TYPE
	SYNTAX        DisplayString (SIZE (0..15))
	MAX-ACCESS    read-only
	STATUS        current 
	DESCRIPTION   "The LED's label name."
	::= { rcChasLedEntry 2 }

rcChasLedStatus OBJECT-TYPE
        SYNTAX        INTEGER {
                         unknown(1),
                         greenSteady(2),
                         greenBlinking(3),
			 amberSteady(4),
			 amberBlinking(5),
			 off(6),
			 redSteady(7),
			 redBlinking(8)
                      }
        MAX-ACCESS    read-only
        STATUS        current 
        DESCRIPTION   "Type of the Led:
                      - unknown(1) - type can not be determined.
		      - greenSteady(2),
                      - greenBlinking(3),
		      - amberSteady(4),
		      - amberBlinking(5),
		      -	off(6),
		      - redSteady(7),
		      - redBlinking(8)
		      For different Led, the meaning of each status is different."
        ::= { rcChasLedEntry 3 }


-- Dip-Switch Group

rcIsolateUnconfigPorts OBJECT-TYPE
        SYNTAX        TruthValue
        MAX-ACCESS    read-only
        STATUS        deprecated
        DESCRIPTION   "Used to indicate whether ports that are unconfigured
                      should be assigned to the 'isolated' VLAN.  Ports
                      assigned to the 'isolated' VLAN can only communicate
                      with the CP port.   If this option is not specified,
                      unconfigured ports will be assigned to the 'default'
                      VLAN"
        ::= { rcDipSwitch 1 }

rcUseFactorySettings OBJECT-TYPE
        SYNTAX        TruthValue
        MAX-ACCESS    read-only
        STATUS        deprecated
        DESCRIPTION   "Used to indicate whether the system should ignore
                      the configuration information stored in NVRAM when
                      the system is booted."   
        ::= { rcDipSwitch 2 }

rcHighPriorityMode OBJECT-TYPE
        SYNTAX        TruthValue
        MAX-ACCESS    read-only
        STATUS        deprecated
        DESCRIPTION   "Used to indicate whether the system is configured
                      to operate in a high priority mode.  The switch can  
                      operate in either a 'best effort' or 'high priority' 
                      mode.  In the 'best effort' setting, the maximum 
                      queue thresholds for the QUIDs are set to 768/768 
                      buffers.  In the 'high priority' mode the setting
                      is 512/768.  This means that in 'high priority' mode
                      the normal priority queue can't have more than 512 
                      buffers, while the high priority queue can have up 
                      to 768." 
        ::= { rcDipSwitch 3 }

-- Table Size Group

rcTblRmonStatSize OBJECT-TYPE
        SYNTAX        Integer32
        MAX-ACCESS    read-only
        STATUS        current
        DESCRIPTION   "Used to indicate the current size of the RMON
                      Statistic table."
        ::= { rcTblSize 1 }

rcTblRmonHistoryControlSize OBJECT-TYPE
        SYNTAX        Integer32
        MAX-ACCESS    read-only
        STATUS        current
        DESCRIPTION   "Used to indicate the current size of the RMON  
                      History Control table." 
        ::= { rcTblSize 2 }

rcTblRmonHistoryEnetSize OBJECT-TYPE
        SYNTAX        Integer32
        MAX-ACCESS    read-only
        STATUS        current
        DESCRIPTION   "Used to indicate the current size of the RMON  
                      History Ethernet table." 
        ::= { rcTblSize 3 }

rcTblRmonAlarmSize OBJECT-TYPE
        SYNTAX        Integer32
        MAX-ACCESS    read-only
        STATUS        current
        DESCRIPTION   "Used to indicate the current size of the RMON  
                      Alarm table." 
        ::= { rcTblSize 4 }

rcTblRmonEventSize OBJECT-TYPE
        SYNTAX        Integer32
        MAX-ACCESS    read-only
        STATUS        current
        DESCRIPTION   "Used to indicate the current size of the RMON  
                      Event table." 
        ::= { rcTblSize 5 }

rcTblRmonLogSize OBJECT-TYPE
        SYNTAX        Integer32
        MAX-ACCESS    read-only
        STATUS        current
        DESCRIPTION   "Used to indicate the current size of the RMON  
                      Log table." 
        ::= { rcTblSize 6 }

rcTblArTblSize OBJECT-TYPE  
        SYNTAX        Integer32
        MAX-ACCESS    read-only  
        STATUS        current  
        DESCRIPTION   "Used to indicate the size of the Address 
                      Translation (AR) table."
        ::= { rcTblSize 7 }


rcTblArFree OBJECT-TYPE  
        SYNTAX        Integer32
        MAX-ACCESS    read-only  
        STATUS        current  
        DESCRIPTION   "Used to indicate the number of free
                      entries that are available in the Address 
                      Translation (AR) table."
        ::= { rcTblSize 8 }

rcTblArNoSpace OBJECT-TYPE  
        SYNTAX        Integer32
        MAX-ACCESS    read-only  
        STATUS        current  
        DESCRIPTION   "Used to indicate the number of entries that could
                      not be added to the Address Translation (AR) table
                      due to lack of space."  
        ::= { rcTblSize 9 }

rcTblArAdded OBJECT-TYPE
        SYNTAX        Integer32
        MAX-ACCESS    read-only
        STATUS        current
        DESCRIPTION   "Used to indicate the number of entries added to
                      the Address Translation (AR) table." 
        ::= { rcTblSize 10 }

rcTblArDeleted OBJECT-TYPE 
        SYNTAX        Integer32
        MAX-ACCESS    read-only 
        STATUS        current 
        DESCRIPTION   "Used to indicate the number of entries deleted to
                      the Address Translation (AR) table."
        ::= { rcTblSize 11 }

rcTblArMacAdded OBJECT-TYPE 
        SYNTAX        Integer32
        MAX-ACCESS    read-only 
        STATUS        current 
        DESCRIPTION   "Used to indicate the number of MAC entries added to
                      the Address Translation (AR) table."
        ::= { rcTblSize 12 }

rcTblArMacDeleted OBJECT-TYPE 
        SYNTAX        Integer32
        MAX-ACCESS    read-only 
        STATUS        current 
        DESCRIPTION   "Used to indicate the number of MAC entries deleted to
                      the Address Translation (AR) table."
        ::= { rcTblSize 13 }

rcTblArMacMoved OBJECT-TYPE 
        SYNTAX        Integer32
        MAX-ACCESS    read-only 
        STATUS        current 
        DESCRIPTION   "Used to indicate the number of MAC entries moved in 
                      the Address Translation (AR) table."
        ::= { rcTblSize 14 }

rcTblArIpAdded OBJECT-TYPE 
        SYNTAX        Integer32
        MAX-ACCESS    read-only 
        STATUS        current 
        DESCRIPTION   "Used to indicate the number of IP entries added to
                      the Address Translation (AR) table."
        ::= { rcTblSize 15 }

rcTblArIpDeleted OBJECT-TYPE  
        SYNTAX        Integer32
        MAX-ACCESS    read-only  
        STATUS        current  
        DESCRIPTION   "Used to indicate the number of IP entries deleted to 
                      the Address Translation (AR) table."    
        ::= { rcTblSize 16 }

rcTblArMcastTblSize OBJECT-TYPE  
        SYNTAX        Integer32
        MAX-ACCESS    read-only  
        STATUS        current  
        DESCRIPTION   "Used to indicate the size of the Multicast 
                      Address Translation (AR) table."
        ::= { rcTblSize 17 }


rcTblArFreeMcastGroups OBJECT-TYPE  
        SYNTAX        Integer32
        MAX-ACCESS    read-only  
        STATUS        current  
        DESCRIPTION   "Used to indicate the number of free multicast
                      groups availabe in the Address Translation (AR) 
                      table."
        ::= { rcTblSize 18 }

rcTblArIpMcastAdded OBJECT-TYPE  
        SYNTAX        Integer32
        MAX-ACCESS    read-only  
        STATUS        current  
        DESCRIPTION   "Used to indicate the number of Ip multicast
                      entries that are added to the Address 
                      Translation (AR) table."
        ::= { rcTblSize 19 }

rcTblArIpMcastDeleted OBJECT-TYPE  
        SYNTAX        Integer32
        MAX-ACCESS    read-only  
        STATUS        current  
        DESCRIPTION   "Used to indicate the number of Ip multicast
                      entries that are deleted from the Address 
                      Translation (AR) table."
        ::= { rcTblSize 20 }

rcTblArVlanByPortAdded OBJECT-TYPE  
        SYNTAX        Integer32
        MAX-ACCESS    read-only  
        STATUS        current  
        DESCRIPTION   "Used to indicate the number of VLAN by port
                      entries that are added to the Address 
                      Translation (AR) table."
        ::= { rcTblSize 21 }

rcTblArVlanByPortDeleted OBJECT-TYPE  
        SYNTAX        Integer32
        MAX-ACCESS    read-only  
        STATUS        current  
        DESCRIPTION   "Used to indicate the number of VLAN by port
                      entries that are deleted from the Address 
                      Translation (AR) table."
        ::= { rcTblSize 22 }

rcTblArVlanByProtocolAdded OBJECT-TYPE  
        SYNTAX        Integer32
        MAX-ACCESS    read-only  
        STATUS        current  
        DESCRIPTION   "Used to indicate the number of Vlans by 
                      Protocol Type entries that are added to 
                      the Address Translation (AR) table."
        ::= { rcTblSize 23 }

rcTblArVlanByProtocolDeleted OBJECT-TYPE  
        SYNTAX        Integer32
        MAX-ACCESS    read-only  
        STATUS        current  
        DESCRIPTION   "Used to indicate the number of Vlans by 
                      Protocol Type entries that are deleted from 
                      the Address Translation (AR) table."
        ::= { rcTblSize 24 }

rcTblArVlanByIpSubnetAdded OBJECT-TYPE  
        SYNTAX        Integer32
        MAX-ACCESS    read-only  
        STATUS        current  
        DESCRIPTION   "Used to indicate the number of VLAN by Ip 
                      entries that are added to the Address 
                      Translation (AR) table."
        ::= { rcTblSize 25 }

rcTblArVlanByIpSubnetDeleted OBJECT-TYPE  
        SYNTAX        Integer32
        MAX-ACCESS    read-only  
        STATUS        current  
        DESCRIPTION   "Used to indicate the number of VLAN by Ip 
                      entries that are deleted from the Address 
                      Translation (AR) table."
        ::= { rcTblSize 26 }

rcTblArIpSubnetsAdded OBJECT-TYPE  
        SYNTAX        Integer32
        MAX-ACCESS    read-only  
        STATUS        current  
        DESCRIPTION   "Used to indicate the number of Ip subnet
                      entries that are added to the Address 
                      Translation (AR) table."
        ::= { rcTblSize 27 }

rcTblArIpSubnetsDeleted OBJECT-TYPE  
        SYNTAX        Integer32
        MAX-ACCESS    read-only  
        STATUS        current  
        DESCRIPTION   "Used to indicate the number of Ip subnet 
                      entries that are deleted from the Address 
                      Translation (AR) table."
        ::= { rcTblSize 28 }

rcTblArRsvpsAdded OBJECT-TYPE  
        SYNTAX        Integer32
        MAX-ACCESS    read-only  
        STATUS        current  
        DESCRIPTION   "Used to indicate the number of RSVP
                      entries that are added to the Address 
                      Translation (AR) table."
        ::= { rcTblSize 29 }

rcTblArRsvpsDeleted OBJECT-TYPE  
        SYNTAX        Integer32
        MAX-ACCESS    read-only  
        STATUS        current  
        DESCRIPTION   "Used to indicate the number of RSVP
                      entries that are deleted from the Address 
                      Translation (AR) table."
        ::= { rcTblSize 30 }


rcTblBrdgFdbSize OBJECT-TYPE  
        SYNTAX        Integer32
        MAX-ACCESS    read-only  
        STATUS        current  
        DESCRIPTION   "Used to indicate the number of entries in the 
                      dot1d forwarding database table."    
        ::= { rcTblSize 31 }

rcTblBrdgStaticSize OBJECT-TYPE  
        SYNTAX        Integer32
        MAX-ACCESS    read-only  
        STATUS        current  
        DESCRIPTION   "Used to indicate the number of entries in the 
                      dot1d Static Address Filtering table."    
        ::= { rcTblSize 32 }

rcTblIpAddrSize OBJECT-TYPE  
        SYNTAX        Integer32
        MAX-ACCESS    read-only  
        STATUS        current  
        DESCRIPTION   "Used to indicate the number of entries in the 
                      IP Address table."    
        ::= { rcTblSize 33 }

rcTblIpForwardingSize OBJECT-TYPE  
        SYNTAX        Integer32
        MAX-ACCESS    read-only   
        STATUS        current   
        DESCRIPTION   "Used to indicate the number of entries in the 
                       IP Forwarding/Best Route table."        
        ::= { rcTblSize 34 }

rcTblIpNetToMediaSize OBJECT-TYPE  
        SYNTAX        Integer32
        MAX-ACCESS    read-only   
        STATUS        current   
        DESCRIPTION   "Used to indicate the number of entries in the 
                      IP Net-to-media table."        
        ::= { rcTblSize 35 }

rcTblIpBestPlusAltRouteSize OBJECT-TYPE  
        SYNTAX        Integer32
        MAX-ACCESS    read-only  
        STATUS        current  
        DESCRIPTION   ""    
        ::= { rcTblSize 36 }

rcTblIpBestPathSize OBJECT-TYPE  
        SYNTAX        Integer32
        MAX-ACCESS    read-only  
        STATUS        current  
        DESCRIPTION   ""    
        ::= { rcTblSize 37 }

rcTblIpBestPlusAltPathSize OBJECT-TYPE  
        SYNTAX        Integer32
        MAX-ACCESS    read-only   
        STATUS        current   
        DESCRIPTION   ""        
        ::= { rcTblSize 38 }


-- rcBoot Group

rcBootFlashSwVersion OBJECT-TYPE
        SYNTAX        DisplayString
        MAX-ACCESS    read-only
        STATUS        obsolete
        DESCRIPTION   "BootFlashSwVersion indicates the software
                      version in the Flash."
        ::= { rcBoot 1 }

rcBootPcmciaSwVersion OBJECT-TYPE
        SYNTAX        DisplayString
        MAX-ACCESS    read-only
        STATUS        obsolete
        DESCRIPTION   "BootPcmciaSwVersion indicate the software
                      version in the Pcmcia card."
        ::= { rcBoot 2 }


rcBootLastBootSource OBJECT-TYPE
        SYNTAX        DisplayString
        MAX-ACCESS    read-only
        STATUS        obsolete
        DESCRIPTION   "Indicates the boot source of the last
                      the system boot."
        ::= { rcBoot 3 } 
 
rcBootPrimary OBJECT-TYPE
        SYNTAX          INTEGER {
                           flash(1),
                           pcmcia(2),
                           net(3),
                           skip(4)
                        }
        MAX-ACCESS        	read-write
        STATUS        	obsolete
        DESCRIPTION   	"BootPrimary is indicator for the
                     	primary source to boot the system."
	DEFVAL 		{ flash }
        ::= { rcBoot 4 } 
 
rcBootSecondary OBJECT-TYPE
        SYNTAX          INTEGER {
                           flash(1),
                           pcmcia(2),
                           net(3),
                           skip(4)
                        }
        MAX-ACCESS        	read-write
        STATUS        	obsolete
        DESCRIPTION   	"BootSecondary indicates the second choice
                        of the boot source."
	DEFVAL 		{ pcmcia }
        ::= { rcBoot 5 } 
 
rcBootTertiary OBJECT-TYPE
        SYNTAX          INTEGER {
                           flash(1),
                           pcmcia(2),
                           net(3),
                           skip(4)
                        }
        MAX-ACCESS        	read-write
        STATUS        	obsolete
        DESCRIPTION   	"BootTertiary indicates the third choice 
                        of boot source."
	DEFVAL 		{ net }
        ::= { rcBoot 6 } 
 

-- rcDevice Group
rcDeviceLastBootSource OBJECT-TYPE
        SYNTAX          DisplayString
        MAX-ACCESS      read-only
        STATUS          deprecated
        DESCRIPTION     "Used to indicate the source of the software
                         image the system was last booted with."
        ::= { rcDevice 1 } 
 
rcDevicePrimarySource OBJECT-TYPE
        SYNTAX          INTEGER {
                           flash(1),
                           pcmcia(2),
                           net(3),
                           skip(4)
                        }
        MAX-ACCESS        	read-write
        STATUS        	deprecated
        DESCRIPTION   	"Used to indicate the primary choice to get
                         a system software image."
        ::= { rcDevice 2 } 
 
rcDevicePrimarySourceFileName OBJECT-TYPE
        SYNTAX          DisplayString (SIZE(0..255))
        MAX-ACCESS      read-write
        STATUS          deprecated
        DESCRIPTION     "Used to indicate a file number, if applicable."
        ::= { rcDevice 3 } 

rcDeviceSecondarySource OBJECT-TYPE
        SYNTAX          INTEGER {
                           flash(1),
                           pcmcia(2),
                           net(3),
                           skip(4)
                        }
        MAX-ACCESS        	read-write
        STATUS        	deprecated
        DESCRIPTION   	"Used to indicate the secondary choice to get
                         a system software image."
        ::= { rcDevice 4 } 
 
rcDeviceSecondarySourceFileName OBJECT-TYPE
        SYNTAX          DisplayString (SIZE(0..255))
        MAX-ACCESS      read-write
        STATUS          deprecated
        DESCRIPTION     "Used to indicate a file name, if applicable."
        ::= { rcDevice 5 } 

rcDeviceTertiarySource OBJECT-TYPE
        SYNTAX          INTEGER {
                           flash(1),
                           pcmcia(2),
                           net(3),
                           skip(4)
                        }
        MAX-ACCESS        	read-write
        STATUS        	deprecated
        DESCRIPTION   	"Used to indicate the tertiary choice to get
                         a system software image."
        ::= { rcDevice 6 } 
 
rcDeviceTertiarySourceFileName OBJECT-TYPE
        SYNTAX          DisplayString (SIZE(0..255))
        MAX-ACCESS      read-write
        STATUS          deprecated
        DESCRIPTION     "Used to indicate a file name, if applicable."
        ::= { rcDevice 7 } 

rcDeviceConfigSource OBJECT-TYPE
        SYNTAX          INTEGER {
                           flash(1),
                           pcmcia(2),
			   nvram(5)
                        }
        MAX-ACCESS        	read-write
        STATUS        	deprecated
        DESCRIPTION   	"Used to indicate the location to get a system 
			configuration file during system boot."
        ::= { rcDevice 8 } 
 
rcDeviceConfigSourceFileName OBJECT-TYPE
        SYNTAX          DisplayString (SIZE(0..255))
        MAX-ACCESS      read-write
        STATUS          deprecated
        DESCRIPTION     "Used to indicate a file name, if applicable."
        ::= { rcDevice 9 } 

rcDeviceFlashBytesUsed OBJECT-TYPE
        SYNTAX          Integer32
        MAX-ACCESS      read-only
        STATUS          deprecated
        DESCRIPTION     "Used to indicate the number of bytes used in the
                         system's configuration flash device."
        ::= { rcDevice 10 } 

rcDeviceFlashBytesFree OBJECT-TYPE
        SYNTAX          Integer32
        MAX-ACCESS      read-only
        STATUS          deprecated
        DESCRIPTION     "Used to indicate the number of bytes available in
                         the system's configuration flash device."
        ::= { rcDevice 11 } 

rcDevicePcmciaBytesUsed OBJECT-TYPE
        SYNTAX          Integer32
        MAX-ACCESS      read-only
        STATUS          deprecated
        DESCRIPTION     "Used to indicate the number of bytes used in the
                         system's PCMCIA device."
        ::= { rcDevice 12 } 

rcDevicePcmciaBytesFree OBJECT-TYPE
        SYNTAX          Integer32
        MAX-ACCESS      read-only
        STATUS          deprecated
        DESCRIPTION     "Used to indicate the number of bytes available in 
                         the system's PCMCIA device."
        ::= { rcDevice 13 } 

rcDeviceAction OBJECT-TYPE
        SYNTAX          INTEGER {
			    none(1),
                            squeezeFlash(2),
                            squeezePcmcia(3),
                            formatFlash(4),
                            formatPcmcia(5),
                            recoverFlash(6), 
                            recoverPcmcia(7) 
                        }
        MAX-ACCESS        	read-write
        STATUS        	deprecated
        DESCRIPTION   	"Used to specify a particular action to perform on
                         one of the system's device."
        ::= { rcDevice 14 } 
 
rcDeviceResult OBJECT-TYPE
        SYNTAX          INTEGER {
                            none(1),
                            inProgress(2),
                            success(3),
                            fail(4)
                        }
        MAX-ACCESS        	read-only
        STATUS        	deprecated
        DESCRIPTION   	"Used to indicate the result of the last action
                         performed on one of the system's device."
        ::= { rcDevice 15 } 
 
rcDeviceFlashNumFiles OBJECT-TYPE
        SYNTAX          Integer32 (0..128)
        MAX-ACCESS      read-only
        STATUS          deprecated
        DESCRIPTION     "Used to indicate the number of files available in
                         the system's configuration flash device."
        ::= { rcDevice 16 }
 
rcDevicePcmciaNumFiles OBJECT-TYPE
        SYNTAX          Integer32 (0..128)
        MAX-ACCESS      read-only
        STATUS          deprecated
        DESCRIPTION     "Used to indicate the number of files available in
                         the system's PCMCIA device."
        ::= { rcDevice 17 }
 

-- The Device Flash Table

rcDeviceFlashTable OBJECT-TYPE
	SYNTAX  	SEQUENCE OF RcDeviceFlashEntry
	MAX-ACCESS  	not-accessible
	STATUS  	deprecated
	DESCRIPTION 	"Flash table."
	::= { rcDevice 25 }
 
rcDeviceFlashEntry OBJECT-TYPE
	SYNTAX  	RcDeviceFlashEntry
	MAX-ACCESS  	not-accessible
	STATUS  	deprecated
	DESCRIPTION 	"An entry in the system's flash table."
	INDEX   { rcDeviceFlashFileNum }
        ::= { rcDeviceFlashTable 1 }
 
RcDeviceFlashEntry ::=
        SEQUENCE {
	     rcDeviceFlashFileNum     Integer32,
	     rcDeviceFlashFileName    DisplayString,
	     rcDeviceFlashFileVersion DisplayString,
	     rcDeviceFlashFileType    INTEGER,
	     rcDeviceFlashFileMode    INTEGER,
	     rcDeviceFlashFileSize    Integer32,
	     rcDeviceFlashFileCrc     Integer32,
	     rcDeviceFlashFileStatus  INTEGER,
	     rcDeviceFlashRowStatus   RowStatus
        }

rcDeviceFlashFileNum OBJECT-TYPE
        SYNTAX  	Integer32 (0..128)
        MAX-ACCESS  	read-only
        STATUS  	deprecated
        DESCRIPTION 	"Used to indicate a particular file in flash."
        ::= { rcDeviceFlashEntry 1 }
 
rcDeviceFlashFileName OBJECT-TYPE
        SYNTAX  	DisplayString
        MAX-ACCESS  	read-only
        STATUS  	deprecated
        DESCRIPTION 	"Used to indicate a flash file's name."
        ::= { rcDeviceFlashEntry 2 }
 
rcDeviceFlashFileVersion OBJECT-TYPE
        SYNTAX  	DisplayString
        MAX-ACCESS  	read-only
        STATUS  	deprecated
        DESCRIPTION 	"Used to indicate the flash file's version."
        ::= { rcDeviceFlashEntry 3 }
 
rcDeviceFlashFileType OBJECT-TYPE
        SYNTAX  	INTEGER {
                           config(1),
                           log(2),
                           trace(3),
                           executable(4)
                        }
        MAX-ACCESS  	read-only
        STATUS  	deprecated
        DESCRIPTION     "Used to indicate the flash file's type."
        ::= { rcDeviceFlashEntry 4 }
 
rcDeviceFlashFileMode OBJECT-TYPE
        SYNTAX  	INTEGER {
                           compressed(1),
                           uncompressed(2)
                        }
        MAX-ACCESS  	read-only
        STATUS  	deprecated
        DESCRIPTION     "Used to indicate the flash file's mode."
        ::= { rcDeviceFlashEntry 5 }
 
rcDeviceFlashFileSize OBJECT-TYPE
        SYNTAX  	Integer32
        MAX-ACCESS  	read-only
        STATUS  	deprecated
        DESCRIPTION     "Used to indicate the flash file's size."
        ::= { rcDeviceFlashEntry 6 }
 
rcDeviceFlashFileCrc OBJECT-TYPE
        SYNTAX  	Integer32
        MAX-ACCESS  	read-only
        STATUS  	deprecated
        DESCRIPTION     "Used to indicate the flash file's CRC."
        ::= { rcDeviceFlashEntry 7 }
 
rcDeviceFlashFileStatus OBJECT-TYPE
        SYNTAX  	INTEGER {
                           active(1),
                           deleted(2)
                        }
        MAX-ACCESS  	read-only
        STATUS  	deprecated
        DESCRIPTION     "Used to indicate the flash file's status.
                         A file that has been marked for deletion, but  
                         who's space has not been reclaimed yet is marked
                         as 'deleted'."
        ::= { rcDeviceFlashEntry 8 }
 
rcDeviceFlashRowStatus OBJECT-TYPE
        SYNTAX  	RowStatus
        MAX-ACCESS  	read-write
        STATUS  	deprecated
        DESCRIPTION 	"Row status."
        ::= { rcDeviceFlashEntry 9 }


-- The Device Pcmcia Table

rcDevicePcmciaTable OBJECT-TYPE
	SYNTAX  	SEQUENCE OF RcDevicePcmciaEntry
	MAX-ACCESS  	not-accessible
	STATUS  	deprecated
	DESCRIPTION 	"PCMCIA table."
	::= { rcDevice 26 }
 
rcDevicePcmciaEntry OBJECT-TYPE
	SYNTAX  	RcDevicePcmciaEntry
	MAX-ACCESS  	not-accessible
	STATUS  	deprecated
        DESCRIPTION     "An entry in the system's PCMCIA table."
	INDEX   { rcDevicePcmciaFileNum }
        ::= { rcDevicePcmciaTable 1 }
 
RcDevicePcmciaEntry ::=
        SEQUENCE {
	     rcDevicePcmciaFileNum     Integer32,
	     rcDevicePcmciaFileName    DisplayString,
	     rcDevicePcmciaFileVersion DisplayString,
	     rcDevicePcmciaFileType    INTEGER,
	     rcDevicePcmciaFileMode     INTEGER,
	     rcDevicePcmciaFileSize    Integer32,
	     rcDevicePcmciaFileCrc     Integer32,
	     rcDevicePcmciaFileStatus  INTEGER,
	     rcDevicePcmciaRowStatus   RowStatus
        }

rcDevicePcmciaFileNum OBJECT-TYPE
        SYNTAX  	Integer32 (0..128)
        MAX-ACCESS  	read-only
        STATUS  	deprecated
        DESCRIPTION     "Used to indicate a particular file in PCMCIA."
        ::= { rcDevicePcmciaEntry 1 }
 
rcDevicePcmciaFileName OBJECT-TYPE
        SYNTAX  	DisplayString
        MAX-ACCESS  	read-only
        STATUS  	deprecated
        DESCRIPTION     "Used to indicate the PCMCIA file's name."
        ::= { rcDevicePcmciaEntry 2 }
 
rcDevicePcmciaFileVersion OBJECT-TYPE
        SYNTAX  	DisplayString
        MAX-ACCESS  	read-only
        STATUS  	deprecated
        DESCRIPTION     "Used to indicate the PCMCIA file's version."
        ::= { rcDevicePcmciaEntry 3 }
 
rcDevicePcmciaFileType OBJECT-TYPE
        SYNTAX  	INTEGER {
                           config(1),
                           log(2),
                           trace(3),
                           executable(4)
                        }
        MAX-ACCESS  	read-only
        STATUS  	deprecated
        DESCRIPTION     "Used to indicate the PCMCIA file's type."
        ::= { rcDevicePcmciaEntry 4 }
 
rcDevicePcmciaFileMode OBJECT-TYPE
        SYNTAX  	INTEGER {
                           compressed(1),
                           uncompressed(2)
                        }
        MAX-ACCESS  	read-only
        STATUS  	deprecated
        DESCRIPTION     "Used to indicate a particular file in mode."
        ::= { rcDevicePcmciaEntry 5 }
 
rcDevicePcmciaFileSize OBJECT-TYPE
        SYNTAX  	Integer32
        MAX-ACCESS  	read-only
        STATUS  	deprecated
        DESCRIPTION     "Used to indicate the PCMCIA file's size."
        ::= { rcDevicePcmciaEntry 6 }
 
rcDevicePcmciaFileCrc OBJECT-TYPE
        SYNTAX  	Integer32
        MAX-ACCESS  	read-only
        STATUS  	deprecated
        DESCRIPTION     "Used to indicate the PCMCIA file's CRC."
        ::= { rcDevicePcmciaEntry 7 }
 
rcDevicePcmciaFileStatus OBJECT-TYPE
        SYNTAX  	INTEGER {
                           active(1),
                           deleted(2)
                        }
        MAX-ACCESS  	read-only
        STATUS  	deprecated
        DESCRIPTION     "Used to indicate the PCMCIA file's status.
                         A file that has been marked for deletion, but
                         who's space has not been reclaimed yet is marked
                         as 'deleted'."
        ::= { rcDevicePcmciaEntry 8 }
 
rcDevicePcmciaRowStatus OBJECT-TYPE
        SYNTAX  	RowStatus
        MAX-ACCESS  	read-write
        STATUS  	deprecated
        DESCRIPTION 	"Row status."
        ::= { rcDevicePcmciaEntry 9 }

-- rcWeb related information

rcWebEnableServer OBJECT-TYPE
        SYNTAX        TruthValue
        MAX-ACCESS    read-write
        STATUS        current
        DESCRIPTION   "Control whether the web server should be enabled.
                      Setting this variable to true will make the server
                      operational.  Setting this variable to false will
                      disable server."
        DEFVAL        { false }
        ::= { rcWeb 1 }

rcWebRWAUserName OBJECT-TYPE
        SYNTAX        DisplayString (SIZE (1..20))
        MAX-ACCESS    read-write
        STATUS        current
        DESCRIPTION   "User name for the read-write-all web-server account."
        ::= { rcWeb 2 }

rcWebRWAPassword OBJECT-TYPE
        SYNTAX        DisplayString (SIZE (1..32))
        MAX-ACCESS    read-write
        STATUS        current
        DESCRIPTION   "Password for the read-write-all web-server account."
        ::= { rcWeb 3 }

rcWebRWUserName OBJECT-TYPE
        SYNTAX        DisplayString (SIZE (1..20))
        MAX-ACCESS    read-write
        STATUS        current
        DESCRIPTION   "User name for the read-write web-server account."
        ::= { rcWeb 4 }
 
rcWebRWPassword OBJECT-TYPE 
        SYNTAX        DisplayString (SIZE (1..32)) 
        MAX-ACCESS    read-write 
        STATUS        current 
        DESCRIPTION   "Password for the read-write web-server account." 
        ::= { rcWeb 5 } 

rcWebROUserName OBJECT-TYPE
        SYNTAX        DisplayString (SIZE (1..20))
        MAX-ACCESS    read-write
        STATUS        current
        DESCRIPTION   "User name for the read-only web-server account."
        ::= { rcWeb 6 }
 
rcWebROPassword OBJECT-TYPE 
        SYNTAX        DisplayString (SIZE (1..32))
        MAX-ACCESS    read-write 
        STATUS        current 
        DESCRIPTION   "Password for the read-only web-server account." 
        ::= { rcWeb 7 } 

rcWebLastChange OBJECT-TYPE 
        SYNTAX        TimeTicks 
        MAX-ACCESS    read-only 
        STATUS        current 
        DESCRIPTION   "Last web-browser initiated configuration
                      change since sysUpTime."
        ::= { rcWeb 8 }
 
rcWebNumHits OBJECT-TYPE
        SYNTAX        Integer32
        MAX-ACCESS    read-only
        STATUS        current
        DESCRIPTION   "Number of hits to the web-server"
	::= { rcWeb 9 } 

rcWebNumAccessChecks OBJECT-TYPE
        SYNTAX        Integer32
        MAX-ACCESS    read-only
        STATUS        current
        DESCRIPTION   "Number of access checks performed by the web-server"
        ::= { rcWeb 10 }

rcWebNumAccessBlocks OBJECT-TYPE
        SYNTAX        Integer32
        MAX-ACCESS    read-only
        STATUS        current
        DESCRIPTION   "Number of accesses blocked by the web-server"
        ::= { rcWeb 11 }

rcWebNumRxErrors OBJECT-TYPE 
        SYNTAX        Integer32
        MAX-ACCESS    read-only 
        STATUS        current 
        DESCRIPTION   "Number of receive errors encountered by the web-server" 
        ::= { rcWeb 12 }

rcWebNumTxErrors OBJECT-TYPE 
        SYNTAX        Integer32
        MAX-ACCESS    read-only 
        STATUS        current 
        DESCRIPTION   "Number of transmit errors encountered by the web-server" 
        ::= { rcWeb 13 }

rcWebNumSetRequest OBJECT-TYPE 
        SYNTAX        Integer32
        MAX-ACCESS    read-only 
        STATUS        current 
        DESCRIPTION   "Number of set-request to the web-server" 
        ::= { rcWeb 14 }

rcWebPrimaryHtmlSourceDir OBJECT-TYPE
        SYNTAX        DisplayString (SIZE(0..64))
        MAX-ACCESS    read-write
        STATUS        current
        DESCRIPTION   "primary html source directory"
	DEFVAL	      { "local" }
        ::= { rcWeb 15 }
 
rcWebSecondaryHtmlSourceDir OBJECT-TYPE
        SYNTAX        DisplayString (SIZE(0..64))
        MAX-ACCESS    read-write
        STATUS        current
        DESCRIPTION   "secondary html source directory"
	DEFVAL	      { "pcmcia" }
        ::= { rcWeb 16 }
 
rcWebTertiaryHtmlSourceDir OBJECT-TYPE
        SYNTAX        DisplayString (SIZE(0..64))
        MAX-ACCESS    read-write
        STATUS        current
        DESCRIPTION   "tertiary html source directory"
        ::= { rcWeb 17 }
 
rcWebRWL3UserName OBJECT-TYPE
        SYNTAX        DisplayString (SIZE (1..20))
        MAX-ACCESS    read-write
        STATUS        current
        DESCRIPTION   "user name for the L3 web server account"
        ::= { rcWeb 18 }
 
rcWebRWL3Password OBJECT-TYPE
        SYNTAX        DisplayString (SIZE (1..32))
        MAX-ACCESS    read-write
        STATUS        current
        DESCRIPTION   "password for the L3 web server account"
        ::= { rcWeb 19 }

rcWebRWL2UserName OBJECT-TYPE
        SYNTAX        DisplayString (SIZE (1..20))
        MAX-ACCESS    read-write
        STATUS        current
        DESCRIPTION   "user name for the L2 web server account"
        ::= { rcWeb 20 }
 
rcWebRWL2Password OBJECT-TYPE
        SYNTAX        DisplayString (SIZE (1..32))
        MAX-ACCESS    read-write
        STATUS        current
        DESCRIPTION   "password for the L2 web server account"
        ::= { rcWeb 21 }
 
rcWebDefaultDisplayRows OBJECT-TYPE
        SYNTAX        Integer32 (10..100)
        MAX-ACCESS    read-write
        STATUS        current
        DESCRIPTION   "default display rows in html page."
	DEFVAL	      { 48 }
        ::= { rcWeb 22 }

rcWebLastHostAccessBlocked OBJECT-TYPE
        SYNTAX        IpAddress
        MAX-ACCESS    read-only
        STATUS        deprecated
        DESCRIPTION   "last host access blocked. This deprecated by
	               rcWebLastHostAccessBlockedAddress"
        ::= { rcWeb 23 }
 
rcWebHelpTftpSourceDir OBJECT-TYPE
        SYNTAX        OCTET STRING (SIZE (0..256))
        MAX-ACCESS    read-write
        STATUS        current
        DESCRIPTION   "tftp source directory for help files"
        ::= { rcWeb 24 }

rcWebHttpPort OBJECT-TYPE
        SYNTAX        Integer32 (1..65535)
        MAX-ACCESS    read-write
        STATUS        current
        DESCRIPTION   "the HTTP port for web access"
	DEFVAL	      { 80 }
        ::= { rcWeb 25 }

rcWebSecureOnly OBJECT-TYPE
        SYNTAX        TruthValue
        MAX-ACCESS    read-write
        STATUS        current
        DESCRIPTION   "Control whether the secure only should be enabled.
         	      Setting this variable to true will make the server support HTTPS only.  
	   	      Setting this variable to false will make the server support both HTTP & HTTPS"
        DEFVAL        { true }
        ::= { rcWeb 26 }

rcWebHttpsPort OBJECT-TYPE
        SYNTAX        Integer32 (443 | 1024..49151)
        MAX-ACCESS    read-write
        STATUS        current
        DESCRIPTION   "the HTTPS port for web access"
	DEFVAL	      { 443 }
        ::= { rcWeb 27 }
 
rcWebLastHostAccessBlockedAddressType OBJECT-TYPE
        SYNTAX 	      InetAddressType
	MAX-ACCESS    read-only
        STATUS        current
        DESCRIPTION   "Address type (IPv4/IPv6) of last host access blocked"
        ::= { rcWeb 28 }

rcWebLastHostAccessBlockedAddress OBJECT-TYPE
        SYNTAX        InetAddress
        MAX-ACCESS    read-only
        STATUS        current
        DESCRIPTION   "last host access blocked"
        ::= { rcWeb 29 }

rcWebInactivityTimeout OBJECT-TYPE
        SYNTAX        Unsigned32(30..65535)
        UNITS         "seconds"
        MAX-ACCESS    read-write
        STATUS        current
        DESCRIPTION   "Used to indicate the amount of idle time, in
     		      seconds to wait before timing out EDM login
		      sessions."
	DEFVAL        { 900 }
        ::= { rcWeb 30 }
    
rcWebTlsMinimumVersion OBJECT-TYPE
        SYNTAX        INTEGER {
                                tlsv10(1),
                                tlsv11(2),
                                tlsv12(3) }
        MAX-ACCESS    read-write
        STATUS        current
        DESCRIPTION   "Specifies the minimum version of TLS protocol supported by the Web Server.
                      tlsv10 sets the version to 1.0.
                      tlsv11 sets the version to 1.1.
                      tlsv12 sets the version to 1.2."
        DEFVAL        { tlsv12 }
        ::= { rcWeb 31 }

rcWebMinimumPasswordLength OBJECT-TYPE
        SYNTAX        Integer32 (1..32)
        MAX-ACCESS    read-write
        STATUS        current
        DESCRIPTION   "Minimum length of password for web user"
        ::= { rcWeb 32 }

rcWebROEnable OBJECT-TYPE
        SYNTAX        TruthValue
        MAX-ACCESS    read-write
        STATUS        current
        DESCRIPTION   "Enable/Disable for the read-only Web Server (EDM) 
	    	       account."
        DEFVAL          { false }
        ::= { rcWeb 33 }        

-- rcCli related information

rcCliRWAUserName OBJECT-TYPE
        SYNTAX        DisplayString (SIZE (1..20))
        MAX-ACCESS    read-write
        STATUS        current
        DESCRIPTION   "User name for the read-write-all CLI account."
        ::= { rcCli 1 }

rcCliRWAPassword OBJECT-TYPE
        SYNTAX        OCTET STRING (SIZE (0..256))
        MAX-ACCESS    read-write
        STATUS        current
        DESCRIPTION   "Password for the read-write-all CLI account."
        ::= { rcCli 2 }

rcCliRWUserName OBJECT-TYPE
        SYNTAX        DisplayString (SIZE (1..20))
        MAX-ACCESS    read-write
        STATUS        current
        DESCRIPTION   "User name for the read-write CLI account."
        ::= { rcCli 3 }
 
rcCliRWPassword OBJECT-TYPE 
        SYNTAX        OCTET STRING (SIZE (0..256)) 
        MAX-ACCESS    read-write 
        STATUS        current 
        DESCRIPTION   "Password for the read-write CLI account." 
        ::= { rcCli 4 } 

rcCliRWL3UserName OBJECT-TYPE
        SYNTAX        DisplayString (SIZE (1..20))
        MAX-ACCESS    read-write
        STATUS        current
        DESCRIPTION   "User name for the read-write layer-3 CLI account."
        ::= { rcCli 5 }

rcCliRWL3Password OBJECT-TYPE
        SYNTAX        DisplayString (SIZE (0..32))
        MAX-ACCESS    read-write
        STATUS        current
        DESCRIPTION   "Password for the read-write layer-3 CLI account."
        ::= { rcCli 6 }

rcCliRWL2UserName OBJECT-TYPE
        SYNTAX        DisplayString (SIZE (1..20))
        MAX-ACCESS    read-write
        STATUS        current
        DESCRIPTION   "User name for the read-write layer-2 CLI account."   
        ::= { rcCli 7 }  
 
rcCliRWL2Password OBJECT-TYPE
        SYNTAX        DisplayString (SIZE (0..32))
        MAX-ACCESS    read-write
        STATUS        current
        DESCRIPTION   "Password for the read-write layer-2 CLI account."
        ::= { rcCli 8 }

rcCliROUserName OBJECT-TYPE
        SYNTAX        DisplayString (SIZE (1..20))
        MAX-ACCESS    read-write
        STATUS        current
        DESCRIPTION   "User name for the read-only CLI account."
        ::= { rcCli 9 }
 
rcCliROPassword OBJECT-TYPE 
        SYNTAX        DisplayString (SIZE (0..32))
        MAX-ACCESS    read-write 
        STATUS        current 
        DESCRIPTION   "Password for the read-only CLI account." 
        ::= { rcCli 10 } 

rcCliMaxTelnetSessions OBJECT-TYPE 
        SYNTAX        Integer32 (0..8)
        MAX-ACCESS    read-write
        STATUS        current
        DESCRIPTION   "Used to indicate the maximum number of telnet
		      sessions the system will support."
	DEFVAL	      { 8 }
	::= { rcCli 11 } 

rcCliMaxRloginSessions OBJECT-TYPE
        SYNTAX        Integer32 (0..8)
        MAX-ACCESS    read-write  
        STATUS        current
        DESCRIPTION   "Used to indicate the maximum number of rlogin
                      sessions the system will support."
	DEFVAL	      { 8 }
        ::= { rcCli 12 }

rcCliTimeout OBJECT-TYPE
        SYNTAX        Integer32 (30..65535)
        MAX-ACCESS    read-write
        STATUS        current
        DESCRIPTION   "Used to indicate the amount of idle time, in
     		      seconds to wait before timing out telnet and 
		      rlogin sessions."
	DEFVAL        { 900 }
        ::= { rcCli 13 }

rcCliNumAccessViolations OBJECT-TYPE
        SYNTAX        Integer32
        MAX-ACCESS    read-only
        STATUS        current
        DESCRIPTION   "Used to indicate the number of CLI access
		      violations detected by the system."
        ::= { rcCli 14 }

rcCliRWL1UserName OBJECT-TYPE
        SYNTAX        DisplayString (SIZE (1..20))
        MAX-ACCESS    read-write
        STATUS        current
        DESCRIPTION   "User name for the read-write layer-1 CLI account."
        ::= { rcCli 15 }
 
rcCliRWL1Password OBJECT-TYPE
        SYNTAX        DisplayString (SIZE (0..32))
        MAX-ACCESS    read-write
        STATUS        current
        DESCRIPTION   "Password for the read-write layer-1 CLI account."
        ::= { rcCli 16 }

rcCliPasswordChange OBJECT-TYPE
        SYNTAX        INTEGER {
                         ro(1),
                         l1(2),
                         l2(3),
                         l3(4),
                         rw(5),
                         rwa(6),
                         slboper(7),
                         l4oper(8),
                         oper(9),
                         slbadmin(10),
                         l4admin(11),
                         ssladmin(12),
                         commStrRo(13),
                         commStrRw(14),
                         commStrl3(15),
                         commStrl2(16),
                         commStrl1(17),
                         webPassWdRo(18),
                         webPassWdRwa(19),
                         auditor(20),
                         security(21),
                         operator(22),
                         privilege(23),
                         administrator(24)
                      }
        MAX-ACCESS    read-only
        STATUS        current
        DESCRIPTION   "Used to indication which password is changed when
                       sending a rcCliPasswordChange trap."
        ::= { rcCli 17 }

rcCliPassChangeResult OBJECT-TYPE
        SYNTAX        INTEGER {
                         success(1),
                         fail(2)
                      }
        MAX-ACCESS    read-only
        STATUS        current
        DESCRIPTION   "Used to indication the result of changing password when
                       sending a rcPasswordChange trap."
        ::= { rcCli 18 }

rcCliRWEnable OBJECT-TYPE
        SYNTAX        TruthValue
        MAX-ACCESS    read-write
        STATUS        current
        DESCRIPTION   "Enable/Disable for the read-write CLI account."
        DEFVAL        { true }
        ::= { rcCli 19 }
 
rcCliRWL1Enable OBJECT-TYPE
        SYNTAX        TruthValue
        MAX-ACCESS    read-write
        STATUS        current
        DESCRIPTION   "Enable/Disable for the read-write-layer1 CLI
                       account."
        DEFVAL        { true }
        ::= { rcCli 20 }
 
rcCliRWL2Enable OBJECT-TYPE
        SYNTAX        TruthValue
        MAX-ACCESS    read-write
        STATUS        current
        DESCRIPTION   "Enable/Disable for the read-write-layer2 CLI
                       account."
        DEFVAL        { true }
        ::= { rcCli 21 }
 
rcCliRWL3Enable OBJECT-TYPE
        SYNTAX        TruthValue
        MAX-ACCESS    read-write
        STATUS        current
        DESCRIPTION   "Enable/Disable for the read-write-layer3 CLI
                       account."
        DEFVAL          { true }
        ::= { rcCli 22 }
 
rcCliROEnable OBJECT-TYPE
        SYNTAX        TruthValue
        MAX-ACCESS    read-write
        STATUS        current
        DESCRIPTION   "Enable/Disable for the read-only CLI account."
        DEFVAL          { true }
        ::= { rcCli 23 }       

rcCliRWAEnable OBJECT-TYPE
        SYNTAX        TruthValue
        MAX-ACCESS    read-only
        STATUS        current
        DESCRIPTION   "Enable/Disable for the Admin CLI account."
        DEFVAL        { true }
        ::= { rcCli 24 }

rcCliOperatorUserName OBJECT-TYPE
        SYNTAX        DisplayString (SIZE (1..20))
        MAX-ACCESS    read-write
        STATUS        current
        DESCRIPTION   "User name for the Operator CLI account."
        ::= { rcCli 25 }

rcCliOperatorPassword OBJECT-TYPE
        SYNTAX        DisplayString (SIZE (8..255))
        MAX-ACCESS    read-write
        STATUS        current
        DESCRIPTION   "Password for the Operator CLI account."
        ::= { rcCli 26 }

rcCliOperatorEnable OBJECT-TYPE
        SYNTAX        TruthValue
        MAX-ACCESS    read-only
        STATUS        current
        DESCRIPTION   "Enable/Disable for the Operator CLI account."
        DEFVAL        { false }
        ::= { rcCli 27 }

rcCliSecurityUserName OBJECT-TYPE
        SYNTAX        DisplayString (SIZE (1..20))
        MAX-ACCESS    read-write
        STATUS        current
        DESCRIPTION   "User name for the Security CLI account."
        ::= { rcCli 28 }

rcCliSecurityPassword OBJECT-TYPE
        SYNTAX        DisplayString (SIZE (8..255))
        MAX-ACCESS    read-write
        STATUS        current
        DESCRIPTION   "Password for the Security CLI account."
        ::= { rcCli 29 }

rcCliSecurityEnable OBJECT-TYPE
        SYNTAX        TruthValue
        MAX-ACCESS    read-only
        STATUS        current
        DESCRIPTION   "Enable/Disable for the Security CLI account."
        DEFVAL        { false }
        ::= { rcCli 30 }

rcCliAuditorUserName OBJECT-TYPE
        SYNTAX        DisplayString (SIZE (1..20))
        MAX-ACCESS    read-write
        STATUS        current
        DESCRIPTION   "User name for the Auditor CLI account."
        ::= { rcCli 31 }

rcCliAuditorPassword OBJECT-TYPE
        SYNTAX        DisplayString (SIZE (8..255))
        MAX-ACCESS    read-write
        STATUS        current
        DESCRIPTION   "Password for the Auditor CLI account."
        ::= { rcCli 32 }

rcCliAuditorEnable OBJECT-TYPE
        SYNTAX        TruthValue
        MAX-ACCESS    read-only
        STATUS        current
        DESCRIPTION   "Enable/Disable for the Auditor CLI account."
        DEFVAL        { false }
        ::= { rcCli 33 }

rcCliPasswordUpperCase OBJECT-TYPE
        SYNTAX        Integer32 (1..9)
        MAX-ACCESS    read-write
        STATUS        current
        DESCRIPTION   "Number of mandatory upper case characters 
	    	       to be included as part of user password,
		       failing which password creation will
		       not succeed"
        ::= { rcCli 34 }

rcCliPasswordLowerCase OBJECT-TYPE
        SYNTAX        Integer32 (1..9)
        MAX-ACCESS    read-write
        STATUS        current
        DESCRIPTION   "Number of mandatory lower case characters 
	    	       to be included as part of user password,
		       failing which password creation will
		       not succeed"
        ::= { rcCli 35 }

rcCliPasswordNumericCase OBJECT-TYPE
        SYNTAX        Integer32 (1..9)
        MAX-ACCESS    read-write
        STATUS        current
        DESCRIPTION   "Number of mandatory numeric characters
	    	       to be included as part of user password,
		       failing which password creation will
		       not succeed"
        ::= { rcCli 36 }

rcCliPasswordSpecialCase OBJECT-TYPE
        SYNTAX        Integer32 (1..9)
        MAX-ACCESS    read-write
        STATUS        current
        DESCRIPTION   "Number of mandatory special characters
	    	       to be included as part of user password,
		       failing which password creation will
		       not succeed"
        ::= { rcCli 37 }

rcCliPasswordChangeInterval OBJECT-TYPE
        SYNTAX      Integer32 (1..999)
        MAX-ACCESS    read-write
        STATUS        current
        DESCRIPTION   "The time interval in which user cannot
	    	       change his password from the last password
		       change"
        ::= { rcCli 38 }

rcCliPasswordPreNotificationInterval1 OBJECT-TYPE
        SYNTAX        Integer32 (1..99)
        MAX-ACCESS    read-write
        STATUS        current
        DESCRIPTION   "The time for first notificateion to be sent to 
	    	       the user before the expiry of user password"
        ::= { rcCli 39 }

rcCliPasswordPreNotificationInterval2 OBJECT-TYPE
        SYNTAX        Integer32 (1..99)
        MAX-ACCESS    read-write
        STATUS        current
        DESCRIPTION   "The time for second notificateion to be sent to 
	    	       the user before the expiry of user password."
        ::= { rcCli 40 }

rcCliPasswordPreNotificationInterval3 OBJECT-TYPE
        SYNTAX        Integer32 (1..99)
        MAX-ACCESS    read-write
        STATUS        current
        DESCRIPTION   "The time for third notificateion to be sent to 
	    	       the user before the expiry of user password."
        ::= { rcCli 41 }

rcCliPasswordPostNotificationInterval1 OBJECT-TYPE
        SYNTAX        Integer32 (1..99)
        MAX-ACCESS    read-write
        STATUS        current
        DESCRIPTION   "The time for first notificateion to be sent to 
	    	       the user after the expiry of user password."
        ::= { rcCli 42 }

rcCliPasswordPostNotificationInterval2 OBJECT-TYPE
        SYNTAX        Integer32 (1..99)
        MAX-ACCESS    read-write
        STATUS        current
        DESCRIPTION   "The time for second notificateion to be sent to 
	    	       the user after the expiry of user password."
        ::= { rcCli 43 }

rcCliPasswordPostNotificationInterval3 OBJECT-TYPE
        SYNTAX        Integer32 (1..99)
        MAX-ACCESS    read-write
        STATUS        current
        DESCRIPTION   "The time for third notificateion to be sent to 
	    	       the user after the expiry of user password."
        ::= { rcCli 44 }

rcCliPasswordAccountIdleTime OBJECT-TYPE
        SYNTAX        Integer32 (1..365)
        MAX-ACCESS    read-write
        STATUS        current
        DESCRIPTION   "Specifies time duration, in days, within which if a 
	    	       user is not logged in, the account gets disabled."
	DEFVAL        { 90 }
        ::= { rcCli 45 }

rcCliPasswordAccountUserName OBJECT-TYPE
        SYNTAX        DisplayString (SIZE(1..255))
        MAX-ACCESS    accessible-for-notify
        STATUS        current
        DESCRIPTION   "Object to be used for ecnUserAccountIdleTimeExpireTrap | 
	    	       rcnAuthenticationFailureLoginAttemptsTrap to indicate
		       that idle time has expired for user account or crossed 
		       max-sessions"
        ::= { rcCli 46 }

rcCliPasswordUserAccessLevel OBJECT-TYPE
        SYNTAX        DisplayString (SIZE(1..20))
        MAX-ACCESS    accessible-for-notify
        STATUS        current
        DESCRIPTION   "Object to be used for ecnUserAccountIdleTimeExpireTrap | 
	    	       rcnAuthenticationFailureLoginAttemptsTrap to indicate
		       that idle time has expired for user account or crossed 
		       max-sessions"
        ::= { rcCli 47 }

rcCliPasswordPostExpiryLogins OBJECT-TYPE
        SYNTAX        Integer32 (1..5)
        MAX-ACCESS    read-write
        STATUS        current
        DESCRIPTION   "Number of allowed logins for a user post the password expiry."
	DEFVAL        { 2 }
        ::= { rcCli 48 }

rcCliLoginAttemptErrorTrapEnable OBJECT-TYPE
        SYNTAX        TruthValue
        MAX-ACCESS    read-write
        STATUS        current
        DESCRIPTION   "Indicates whether to send trap upon receiving a login 
	    	       attempt error in the system."
	DEFVAL        { true }
        ::= { rcCli 49 }

rcCliUserTable OBJECT-TYPE
        SYNTAX          SEQUENCE OF RcCliUserEntry
        MAX-ACCESS      not-accessible
        STATUS          current
        DESCRIPTION     "Table of user entries."
        ::= { rcCli 50 }

rcCliUserEntry OBJECT-TYPE
        SYNTAX          RcCliUserEntry
        MAX-ACCESS      not-accessible
        STATUS          current
        DESCRIPTION     "User Table Entry."
        INDEX           { rcCliUserId }
        ::= { rcCliUserTable 1 }

RcCliUserEntry ::=
        SEQUENCE {
                rcCliUserId          Integer32,
                rcCliUserName        DisplayString,
                rcCliUserPassword    OCTET STRING,
                rcCliUserLevel       INTEGER,
                rcCliUserEnable      TruthValue,
                rcCliUserType        INTEGER,
                rcCliUserRowStatus   RowStatus
        }

rcCliUserId OBJECT-TYPE
        SYNTAX          Integer32 (1..10)
        MAX-ACCESS      not-accessible
        STATUS          current
        DESCRIPTION     "User id, which uniquely identify a user."
        ::= { rcCliUserEntry 1 }

rcCliUserName OBJECT-TYPE
        SYNTAX          DisplayString (SIZE (1..20))
        MAX-ACCESS      read-create
        STATUS          current
        DESCRIPTION     "User name. It must be unique."
        ::= { rcCliUserEntry 2 }

rcCliUserPassword OBJECT-TYPE
        SYNTAX          OCTET STRING (SIZE (0..256))
        MAX-ACCESS      read-create
        STATUS          current
        DESCRIPTION     "User password."
        ::= { rcCliUserEntry 3 }

rcCliUserLevel OBJECT-TYPE
        SYNTAX          INTEGER {
                         ro(1),
                         rw(2),
                         rwa(3)
                        }
        MAX-ACCESS      read-create
        STATUS          current
        DESCRIPTION     "User role. It is set at the creation and 
	    		 cannot be changed later. A new user can 
			 have any value, ro, rw or rwa."
        ::= { rcCliUserEntry 4 }

rcCliUserEnable OBJECT-TYPE
        SYNTAX          TruthValue
        MAX-ACCESS      read-create
        STATUS          current
        DESCRIPTION     "Enable/Disable for the user. If the user 
	    		is enabled, it can be used to login to a session."
        DEFVAL        { true }
        ::= { rcCliUserEntry 5 }

rcCliUserType OBJECT-TYPE
        SYNTAX          INTEGER {
                         default(1),
                         userDefined(2)
                        } 
        MAX-ACCESS      read-only
        STATUS          current
        DESCRIPTION     "User Type. It is default for default users 
	    		(ro, rw, rwa) or userDefined for new created users."
        ::= { rcCliUserEntry 6 }

rcCliUserRowStatus OBJECT-TYPE
        SYNTAX          RowStatus
        MAX-ACCESS      read-create
        STATUS          current
        DESCRIPTION     "Used to create/delete entries in rcCliUserTable. 
	    		Default users (ro, rw, rwa) cannot be deleted."
        ::= { rcCliUserEntry 7 }

-- rcCoreDumpGlobals
rcCoreDumpGlobal OBJECT IDENTIFIER ::= { rcCoreDump 1 }

rcCoreDumpGlobalCoreDumpEnable  OBJECT-TYPE
        SYNTAX        EnableValue
        MAX-ACCESS    read-write
        STATUS        current
        DESCRIPTION   "Enable/disable the Core dump functionality"
        DEFVAL { enable }
        ::= { rcCoreDumpGlobal 1 }  
        
rcCoreDumpGlobalCoreDumpDirectory  OBJECT-TYPE
        SYNTAX        DisplayString (SIZE(0..255))
        MAX-ACCESS    read-write
        STATUS        current
        DESCRIPTION   "Core dump create directory. This specifies 
            the directory in which the core dump files is created. 
            The core dump is created in PCMCIA, the path should contain 
            /pcmcia, if the specified path does not start with /pcmcia 
            the specified directory is created in PCMCIA."
        DEFVAL {"/pcmcia/cv/"}
        ::= {  rcCoreDumpGlobal 2 }

-- rcCsuGlobals

rcCsuGlobal OBJECT IDENTIFIER ::= { rcCsu 1 }

rcCsuGlobalStartUpMode OBJECT-TYPE
         SYNTAX          INTEGER {
			   automatic(1),
			   manual(2),
			   none(3)	 
			 }
         MAX-ACCESS      read-only
         STATUS          current
         DESCRIPTION     "Mode of CSU StartUp(Manual/Auto/None). None may not be used"
         ::= { rcCsuGlobal 1 }


-- rcCsuInfo
rcCsuInfoTable OBJECT-TYPE
        SYNTAX          SEQUENCE OF RcCsuInfoEntry
        MAX-ACCESS      not-accessible
        STATUS          current
        DESCRIPTION     "Table of CSU Info Entries."
        ::= { rcCsu 2  }
  
rcCsuInfoEntry OBJECT-TYPE
        SYNTAX          RcCsuInfoEntry
        MAX-ACCESS      not-accessible
        STATUS          current
        DESCRIPTION     "CSU Info Table Entry."
        INDEX           { rcCsuInfoSlotNumber }
        ::= { rcCsuInfoTable 1 }
  
RcCsuInfoEntry ::=
        SEQUENCE {
                rcCsuInfoSlotNumber            Integer32,
                rcCsuInfoTypeOfCard            INTEGER,
                rcCsuInfoTypeOfCardDesc        DisplayString,
                rcCsuInfoUpgradeStatus         INTEGER,
                rcCsuInfoUpgradeStartTime      DateAndTime,
                rcCsuInfoUpgradeEndTime        DateAndTime
        }

rcCsuInfoSlotNumber OBJECT-TYPE
        SYNTAX          Integer32 (1..10)
        MAX-ACCESS      not-accessible
        STATUS          current
        DESCRIPTION     "Value of the slot number."
        ::= { rcCsuInfoEntry 1 }

rcCsuInfoTypeOfCard OBJECT-TYPE
        SYNTAX          INTEGER {
                         none(1),
                         atm(2),
                         pos(3),
                         wsm(4),
                         ssl(5),
                         rmod(6),
                         esm(7),
                         cpu(8),
                         others(9)
                        }
        MAX-ACCESS      read-only
        STATUS          current
        DESCRIPTION     "Integer holding the card type."
        ::= { rcCsuInfoEntry 2 }

rcCsuInfoTypeOfCardDesc OBJECT-TYPE
        SYNTAX          DisplayString (SIZE (0..40))
        MAX-ACCESS      read-only
        STATUS          current
        DESCRIPTION     "The type of card present in the current slot."
        ::= { rcCsuInfoEntry 3 }

rcCsuInfoUpgradeStatus OBJECT-TYPE
        SYNTAX          INTEGER {
                         notApplicable(1),
                         required(2),
                         inProgress(3),
                         complete(4)
                        }
        MAX-ACCESS      read-only
        STATUS          current
        DESCRIPTION     "The Upgrade Status of the card."
        ::= { rcCsuInfoEntry 4 }

rcCsuInfoUpgradeStartTime OBJECT-TYPE
        SYNTAX          DateAndTime
        MAX-ACCESS      read-only
        STATUS          current
        DESCRIPTION     "Timestamp of the upgrade start time."
        ::= { rcCsuInfoEntry 5 }

rcCsuInfoUpgradeEndTime OBJECT-TYPE
        SYNTAX          DateAndTime
        MAX-ACCESS      read-only
        STATUS          current
        DESCRIPTION     "Timestamp of the upgrade end time."
        ::= { rcCsuInfoEntry 6 }

-- CSU Info Table end

-- Syslog Group
 
rcSyslogGlobal      OBJECT IDENTIFIER ::= { rcSyslog 1 }

rcSyslogGlobalEnable OBJECT-TYPE
        SYNTAX        	TruthValue
        MAX-ACCESS        	read-write
        STATUS        	current
        DESCRIPTION   	"Used to enable/disable the SysLog feature.  When
			enabled this feature will send a message to a server 
			on a network that this configured to receive and
			store diagnostic messages from this device.  The
			type of messages sent is user configurable."
	DEFVAL	      	{ true }
        ::= { rcSyslogGlobal 1 }

rcSyslogGlobalMaxHosts OBJECT-TYPE
        SYNTAX        Integer32 (0..10)
        MAX-ACCESS    read-write
        STATUS        current
        DESCRIPTION   "Maximun number of remote hosts considered 'active'
                       and able to receive messages from the Syslog service
                       on the router."
        DEFVAL        { 5 }
        ::= { rcSyslogGlobal 2 }

rcSyslogGlobalOperState OBJECT-TYPE
        SYNTAX        INTEGER {
                         active(1),
                         inactive(2),
                         emptyHostTbl(3),
                         allHostDisabled(4)
                      }
        MAX-ACCESS    read-only
        STATUS        current
        DESCRIPTION   "The operational state of the syslog service
                       on the router."
        DEFVAL        { active }
        ::= { rcSyslogGlobal 3 }

rcSyslogGlobalHeader OBJECT-TYPE
         SYNTAX        INTEGER {
                          default(1),
                          managementVIP(2),
                          circuitlessIP(3)
                       }   
         MAX-ACCESS    read-write
         STATUS        current
         DESCRIPTION   "The IP Header Type for the Syslog Packet."
         DEFVAL        { 1 }
         ::= { rcSyslogGlobal 4 }

rcSyslogGlobalIncludeHostIp OBJECT-TYPE
        SYNTAX        TruthValue
        MAX-ACCESS    read-write
        STATUS        current
        DESCRIPTION   "By default, the Host Ip address is placed at the second field
	               which is after the timestamp and before the log message.
		       The Host Ip is allowed the syslog server to identify the device
		       which the message is received from.
		       
		       In order to support the legacy message format which does not include
		       the Host Ip. This object is introduced to allow user to disable the
		       Host Ip. That means not to send the Host Ip in the log message"
        DEFVAL        { true }
        ::= { rcSyslogGlobal 5 }

rcSyslogHostTbl OBJECT-TYPE
        SYNTAX        SEQUENCE OF RcSyslogHostEntry
        MAX-ACCESS    not-accessible
        STATUS        current
        DESCRIPTION   "Table of remote host destinations for syslog."
        ::= { rcSyslog 2 }

rcSyslogHostEntry OBJECT-TYPE
        SYNTAX        RcSyslogHostEntry
        MAX-ACCESS    not-accessible
        STATUS        current
        DESCRIPTION   "Entry containing information for a particular
                       entry in rcSyslogHostTable."
        INDEX         { rcSyslogHostId }
        ::= { rcSyslogHostTbl 1 }

RcSyslogHostEntry ::= SEQUENCE {
                rcSyslogHostId                  Integer32,
                rcSyslogHostIpAddr              IpAddress,
                rcSyslogHostUdpPort             Integer32,
		rcSyslogHostFacility            INTEGER,	
		rcSyslogHostModuleId            INTEGER,
		rcSyslogHostModuleId2           Integer32,
		rcSyslogHostSeverity            Integer32,
		rcSyslogHostMapInfoSeverity     INTEGER,
		rcSyslogHostMapWarningSeverity  INTEGER,
		rcSyslogHostMapErrorSeverity    INTEGER,
		rcSyslogHostMapMfgSeverity      INTEGER,
		rcSyslogHostMapFatalSeverity    INTEGER,
		rcSyslogHostMapTraceMsg         INTEGER,
		rcSyslogHostMapTrapMsg          INTEGER,
		rcSyslogHostLogTraceMsgs        TruthValue,
		rcSyslogHostLogTrapMsgs         TruthValue,
		rcSyslogHostEnable              TruthValue,
                rcSyslogHostRowStatus           RowStatus,
		rcSyslogHostAddressType         InetAddressType,
		rcSyslogHostAddress             InetAddress,
	  	rcSyslogHostSecureForwardingEnable TruthValue, 
                rcSyslogHostSecureForwardingSshProtect TruthValue,
                rcSyslogHostSecureForwardingTcpPort Integer32,
		rcSyslogHostSecureForwardingMode INTEGER,
		rcSyslogHostSecureForwardingServerCertName DisplayString
        }

rcSyslogHostId OBJECT-TYPE
        SYNTAX        Integer32 (1..10)
        MAX-ACCESS    read-only
        STATUS        current
        DESCRIPTION   "Host Id."
        ::= { rcSyslogHostEntry 1 }

rcSyslogHostIpAddr OBJECT-TYPE
        SYNTAX        IpAddress
        MAX-ACCESS    read-write
        STATUS        current
        DESCRIPTION   "Host Ip Address"
        ::= { rcSyslogHostEntry 2 }

rcSyslogHostUdpPort OBJECT-TYPE
        SYNTAX        Integer32 (514..530)
        MAX-ACCESS    read-write
        STATUS        current
        DESCRIPTION   "Specifies the UDP port to use to send syslog 
                      messages to the host." 
        DEFVAL        { 514 }
        ::= { rcSyslogHostEntry 3 }

rcSyslogHostFacility OBJECT-TYPE
        SYNTAX        INTEGER {
                         local0(128),
                         local1(136),
                         local2(144),
                         local3(152),
                         local4(160),
                         local5(168),
                         local6(176),
                         local7(184)
                      }
        MAX-ACCESS    read-write
        STATUS        current
        DESCRIPTION   "Specifies the UNIX facility used in messages
 		      to the syslog host.  Default is LOCAL7."
        DEFVAL        { local7 }
        ::= { rcSyslogHostEntry 4 }
 
rcSyslogHostModuleId OBJECT-TYPE
        SYNTAX        INTEGER {
                         common         (1),      -- '00000001'H
                         snmp           (2),      -- '00000002'H
                         rmon           (4),      -- '00000004'H
                         portmgr        (8),      -- '00000008'H
                         chasmgr       (16),      -- '00000010'H
                         bridge        (32),      -- '00000020'H
                         ospf          (64),      -- '00000040'H
                         hwif         (128),      -- '00000080'H
                         sim          (256),      -- '00000100'H
                         cpp          (512),      -- '00000200'H
                         netdrv      (1024),      -- '00000400'H
                         vlanmgr     (2048),      -- '00000800'H
                         cli         (4096),      -- '00001000'H
                         main        (8192),      -- '00002000'H
                         p2ip       (16384),      -- '00004000'H
                         rcip       (32768),      -- '00008000'H
                         rompager   (65536),      -- '00010000'H
                         acif      (131072),      -- '00020000'H
                         gbip      (262144),      -- '00040000'H
                         wdt       (524288),      -- '00080000'H
                         tdp      (1048576),      -- '00100000'H
                         mandiag  (2097152),      -- '00200000'H
                         mantest  (4194304),      -- '00400000'H
                         igmp     (8388608),      -- '00800000'H
                         ipfil   (16777216),      -- '01000000'H
                         mlt     (33554432),      -- '02000000'H
                         ippolicy(67108864),      -- '04000000'H
                         ipmc   (134217728),      -- '08000000'H
                         syslog (268435456)       -- '10000000'H
                      }
        MAX-ACCESS    read-write
        STATUS        current
        DESCRIPTION   "Specifies for which modules/tasks syslog messages
		       should be sent.  Default is all modules/tasks."
        ::= { rcSyslogHostEntry 5 }

rcSyslogHostModuleId2 OBJECT-TYPE
        SYNTAX        Integer32
        MAX-ACCESS    read-write
        STATUS        current
        DESCRIPTION   "Specifies for which modules/tasks syslog messages
                       should be sent.  Default is all modules/tasks."
        ::= { rcSyslogHostEntry 6 }

rcSyslogHostSeverity OBJECT-TYPE
        SYNTAX        Integer32 (1..31)
        MAX-ACCESS    read-write
        STATUS        current
        DESCRIPTION   "Specifies the severity level for which syslog messages
		       should be sent for the modules specifies in 
                       'SyslogHostModule'.
                       Value is one of multiple (logical 'OR') of the following:
                         info(1),
                         warning(2),
                         error(4),
                         mfg(8),
                         fatal(16)."
        DEFVAL        { 1 }
        ::= { rcSyslogHostEntry 7 }

rcSyslogHostMapInfoSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
		       INFO messages.  Default is INFO."
        DEFVAL        { info }
        ::= { rcSyslogHostEntry 8 }

rcSyslogHostMapWarningSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       WARNING messages.  Default is WARNING.  Should be
                       less than or equal to INFO."
        DEFVAL        { warning }
        ::= { rcSyslogHostEntry 9 }

rcSyslogHostMapErrorSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       ERROR messages.  Default is ERROR.  Should be
		           less than or equal to WARNING."
        DEFVAL        { error }
        ::= { rcSyslogHostEntry 10 }

rcSyslogHostMapMfgSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       Manufactoring messages.  Dafault is ERROR."
        DEFVAL        { error }
        ::= { rcSyslogHostEntry 11 }

rcSyslogHostMapFatalSeverity OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for Accelar
                       FATAL messages.  Default is EMERGENCY.  Should be
		           less than or equal to ERROR."
        DEFVAL        { emergency }
        ::= { rcSyslogHostEntry 12 }

rcSyslogHostMapTraceMsg OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the syslog severity to use for syslog
		       trace messages.  Default is DEBUG."
        ::= { rcSyslogHostEntry 13 }

rcSyslogHostMapTrapMsg OBJECT-TYPE
        SYNTAX        INTEGER {
                         emergency(1),
                         alert(2),
                         critical(3),
                         error(4),
                         warning(5),
                         notice(6),
                         info(7),
                         debug(8)
                      }
        MAX-ACCESS    read-write
        STATUS        current
        DESCRIPTION   "Specifies the UNIX severity code to use for syslog
		       messages for SNMP traps sent to the syslog host.
                       Default is INFO."
        ::= { rcSyslogHostEntry 14 }

rcSyslogHostLogTraceMsgs OBJECT-TYPE
        SYNTAX        TruthValue
        MAX-ACCESS    read-write
        STATUS        current
        DESCRIPTION   "Indicate whether to activate the host to log the 
                       syslog trace messages."
        ::= { rcSyslogHostEntry 15 }

rcSyslogHostLogTrapMsgs OBJECT-TYPE
        SYNTAX        TruthValue
        MAX-ACCESS    read-write
        STATUS        current
        DESCRIPTION   "Indicate whether to activate the host to log the
	               syslog messages for SNMP traps."
        ::= { rcSyslogHostEntry 16 }

rcSyslogHostEnable OBJECT-TYPE
        SYNTAX        TruthValue
        MAX-ACCESS    read-write
        STATUS        current
        DESCRIPTION   "Enable/Disable messages to be sent to syslog host."
        DEFVAL        { false }
        ::= { rcSyslogHostEntry 17 }

rcSyslogHostRowStatus OBJECT-TYPE
        SYNTAX        RowStatus
        MAX-ACCESS    read-write
        STATUS        current
        DESCRIPTION   "Used to create/delete entries in the rcSyslogTable."
        ::= { rcSyslogHostEntry 18 }
    
rcSyslogHostAddressType OBJECT-TYPE
        SYNTAX        InetAddressType
        MAX-ACCESS    read-write
        STATUS        current
        DESCRIPTION   "Address Type of the Host."
        ::= {rcSyslogHostEntry  19 }

rcSyslogHostAddress OBJECT-TYPE
        SYNTAX        InetAddress
        MAX-ACCESS    read-write
        STATUS        current
        DESCRIPTION   "Address of the Host."
        ::= {rcSyslogHostEntry  20 }

rcSyslogHostSecureForwardingEnable OBJECT-TYPE
        SYNTAX        TruthValue
        MAX-ACCESS    read-write
        STATUS        deprecated
        DESCRIPTION   "Enable/Disable Secure forwarding of Syslog for a particular host.
	               Deprecate/Obsolete by rcSyslogHostSecureForwardingMode"
        DEFVAL        { true }
        ::= { rcSyslogHostEntry  21 }

rcSyslogHostSecureForwardingSshProtect OBJECT-TYPE
        SYNTAX        TruthValue
        MAX-ACCESS    read-write
        STATUS        deprecated
        DESCRIPTION   "Enable/Disable Secure forwarding of Syslog over SSH remote port forwarding
	               for particular host.
	               deprecate/Obsolete by rcSyslogHostSecureForwardingMode "
        DEFVAL        { true }
        ::= { rcSyslogHostEntry  22 }

rcSyslogHostSecureForwardingTcpPort OBJECT-TYPE
        SYNTAX        Integer32(1025..49151)
        MAX-ACCESS    read-write
        STATUS        current
        DESCRIPTION   "Specifies the tcp port to use for Secure forwarding of for particular host."
        DEFVAL        { 1025 }
        ::= { rcSyslogHostEntry  23 }
    
rcSyslogHostSecureForwardingMode   OBJECT-TYPE
        SYNTAX        INTEGER {
	                 none(1),
			 ssh(2),
			 tls(3)
		      }
        MAX-ACCESS    read-write
        STATUS        current
	DESCRIPTION   "Set Secure forwarding mode for a particular Syslog host. This object is
	              used to obsolete the rcSyslogHostSecureForwardingEnable and
		      rcSyslogHostSecureForwardingSshProtect.
		      ssh  - Set Secure forwarding mode for particular Syslog host over SSH tunnel 
		      tls  -  Set Secure forwarding mode for particular Syslog host over TLS 
		      none - Set Secure forwarding mode none for particular Syslog host"
        DEFVAL        { none }
        ::= { rcSyslogHostEntry  24 }

rcSyslogHostSecureForwardingServerCertName   OBJECT-TYPE
        SYNTAX        DisplayString (SIZE (0..64))
        MAX-ACCESS    read-write
        STATUS        current
	DESCRIPTION   "Specifies the identity name of server certificate. It is used to match
	    	       the subject name of the server certificate received during negotiation
		       with this configured server cert name to allow negotiation"
        ::= { rcSyslogHostEntry  25 }
    
-- logging msg control     
rcLogMsgControl OBJECT IDENTIFIER ::= { rcSyslog 3 }

rcLogMsgControlAction OBJECT-TYPE
     SYNTAX      INTEGER{ 
                     suppressMsg(1) , 
		     sendTrap(2),
		     both(3)
                 }
     MAX-ACCESS   read-write
     STATUS       current
     DESCRIPTION      " This value indicates the type of message control action"
     DEFVAL    { suppressMsg }
     ::= { rcLogMsgControl 1 }


rcLogMsgControlInterval OBJECT-TYPE
     SYNTAX         INTEGER (1..30)
     MAX-ACCESS     read-write
     STATUS         current
     DESCRIPTION    "Indicates  the message control interval value in minutes"
     DEFVAL         { 5 }
     ::= { rcLogMsgControl 2}
     
rcLogMsgControlMaxMsgNum OBJECT-TYPE 
     SYNTAX        INTEGER (2..500)
     MAX-ACCESS    read-write
     STATUS        current
     DESCRIPTION   "Used to specify the maximum frequency/count
                    of the occurence of the Log Message."
     DEFVAL        { 5 }
        ::= { rcLogMsgControl 3 }

rcLogMsgControlEnable  OBJECT-TYPE
      SYNTAX        TruthValue
      MAX-ACCESS    read-write
      STATUS        current
      DESCRIPTION   "Indicates the status of the system message control"
      DEFVAL        { false }
      ::={ rcLogMsgControl 4 }

-- logging config

rcLogLoggingGlobal OBJECT IDENTIFIER ::= { rcSyslog 4 }

rcLogLoggingEnable  OBJECT-TYPE
      SYNTAX        TruthValue
      MAX-ACCESS    read-only
      STATUS        current
      DESCRIPTION   "Indicates the status of the logging operational status"
      ::={ rcLogLoggingGlobal 1}
      
rcLogLoggingLevel OBJECT-TYPE 
     SYNTAX        INTEGER {
                      info(1),
		      warning(2),
		      error(3),
		      mfg(4),
		      fatal(5)
                   }     
     MAX-ACCESS    read-write
     STATUS        current
     DESCRIPTION   "Use to set the logging msg level.
                    'info(1)' logs any message level 1 and above.
		    'warning(2)' logs any message level 2 and above.
		    'error(3)' logs any message level 3 and above.
		    'mfg(4)' logs any message level 4 and above.
		    'fatal(5)' logs message level 5 only"
		     
     DEFVAL        { info }
        ::= { rcLogLoggingGlobal 2 }
    
--SyslogRootCertificate Tbl

rcSyslogRootCertificateTable OBJECT-TYPE
      SYNTAX        SEQUENCE OF RcSyslogRootCertificateEntry
      MAX-ACCESS    not-accessible
      STATUS        current
      DESCRIPTION   "Table containing file-name and actio to be performed 
	    	     on the serever root certificate"
      ::= { rcSyslog 5 }


rcSyslogRootCertificateEntry OBJECT-TYPE
      SYNTAX        RcSyslogRootCertificateEntry
      MAX-ACCESS    not-accessible
      STATUS        current
      DESCRIPTION   "Entry containing name of the server root certificate and 
                     the action to be performed on it"
      INDEX         { rcSyslogRootCertificateFilename }
      ::= { rcSyslogRootCertificateTable 1 }

RcSyslogRootCertificateEntry ::= SEQUENCE {
            rcSyslogRootCertificateFilename        DisplayString,
            rcSyslogRootCertificateAction          INTEGER,
            rcSyslogRootCertificateRowStatus       RowStatus
      }


rcSyslogRootCertificateFilename  OBJECT-TYPE
      SYNTAX        DisplayString (SIZE (1..128))
      MAX-ACCESS    not-accessible
      STATUS        current
      DESCRIPTION   "Root certificate file of a Syslog Server to be installed 
	  	     or uninstalled. It requires object rcSyslogRootCertificate
		     to be install or uninstall or none"
      ::= { rcSyslogRootCertificateEntry 1 }

rcSyslogRootCertificateAction  OBJECT-TYPE
      SYNTAX        INTEGER {
                           noAction(1),
                           install(2),
                           uninstall(3) }
      MAX-ACCESS    read-create
      STATUS        current
      DESCRIPTION   "To install/uninstall Root certificate file of a Syslog 
	             Server. It requires the object 
		     rcSyslogGlobalSecureForwadingCertFilename with a valid 
		     certification file. it always return noAction for query"
      DEFVAL        { noAction }
      ::= { rcSyslogRootCertificateEntry 2 }


rcSyslogRootCertificateRowStatus OBJECT-TYPE
      SYNTAX        RowStatus
      MAX-ACCESS    read-create
      STATUS        current
      DESCRIPTION   "Used to create/delete entries in the 
	  	     rcSyslogRootCertificateTable."
      ::= { rcSyslogRootCertificateEntry 3 }

   
-- System Time Grp

rcUserSetTimeYear OBJECT-TYPE
        SYNTAX        Integer32 (1998..2097)
        MAX-ACCESS    read-write
        STATUS        current
        DESCRIPTION   "Year of the time."
        DEFVAL {1998}
        ::= { rcUserSetTime 1 }

rcUserSetTimeMonth OBJECT-TYPE
        SYNTAX        Integer32 (1..12)
        MAX-ACCESS    read-write
        STATUS        current
        DESCRIPTION   "Month of the time."
        DEFVAL {1}
        ::= { rcUserSetTime 2 }

rcUserSetTimeDate OBJECT-TYPE
        SYNTAX        Integer32 (1..31)
        MAX-ACCESS    read-write
        STATUS        current
        DESCRIPTION   "Date of the time."
        DEFVAL {1}
        ::= { rcUserSetTime 3 }

rcUserSetTimeHour OBJECT-TYPE
        SYNTAX        Integer32 (0..23)
        MAX-ACCESS    read-write
        STATUS        current
        DESCRIPTION   "Hour of the time."
        DEFVAL {0}
        ::= { rcUserSetTime 4 }

rcUserSetTimeMinute OBJECT-TYPE
        SYNTAX        Integer32 (0..59)
        MAX-ACCESS    read-write
        STATUS        current
        DESCRIPTION   "Minute of the time."
        DEFVAL {0}
        ::= { rcUserSetTime 5 }

rcUserSetTimeSecond OBJECT-TYPE
        SYNTAX        Integer32 (0..59)
        MAX-ACCESS    read-write
        STATUS        current
        DESCRIPTION   "Second of the time."
        DEFVAL {0}
        ::= { rcUserSetTime 6 }

rcUserSetTimeTimezone OBJECT-TYPE
	SYNTAX        INTEGER {
				cet(1),
				cst6Cdt(2),
				cuba(3),
				eet(4),
				est(5),
				est5Edt(6),
				egypt(7),
				eire(8),
				factory(9),
				gb(10),
				gbEire(11),
				gmt(12),
				gmtE0(13),
				gmtW0(14),
				gmt0(15),
				greenwich(16),
				hst(17),
				hongkong(18),
				iceland(19),
				iran(20),
				israel(21),
				jamaica(22),
				japan(23),
				kwajalein(24),
				libya(25),
				met(26),
				mst(27),
				mst7MDT(28),
				nz(29),
				nzCHAT(30),
				navajo(31),
				prc(32),
				pst8PDT(33),
				poland(34),
				portugal(35),
				roc(36),
				rok(37),
				singapore(38),
				turkey(39),
				uct(40),
				utc(41),
				universal(42),
				wSU(43),
				wet(44),
				zulu(45),
				africa-Abidjan(46),
				africa-Accra(47),
				africa-AddisAbaba(48),
				africa-Algiers(49),
				africa-Asmera(50),
				africa-Bamako(51),
				africa-Bangui(52),
				africa-Banjul(53),
				africa-Bissau(54),
				africa-Blantyre(55),
				africa-Brazzaville(56),
				africa-Bujumbura(57),
				africa-Cairo(58),
				africa-Casablanca(59),
				africa-Ceuta(60),
				africa-Conakry(61),
				africa-Dakar(62),
				africa-DarEsSalaam(63),
				africa-Djibouti(64),
				africa-Douala(65),
				africa-ElAaiun(66),
				africa-Freetown(67),
				africa-Gaborone(68),
				africa-Harare(69),
				africa-Johannesburg(70),
				africa-Kampala(71),
				africa-Khartoum(72),
				africa-Kigali(73),
				africa-Kinshasa(74),
				africa-Lagos(75),
				africa-Libreville(76),
				africa-Lome(77),
				africa-Luanda(78),
				africa-Lubumbashi(79),
				africa-Lusaka(80),
				africa-Malabo(81),
				africa-Maputo(82),
				africa-Maseru(83),
				africa-Mbabane(84),
				africa-Mogadishu(85),
				africa-Monrovia(86),
				africa-Nairobi(87),
				africa-Ndjamena(88),
				africa-Niamey(89),
				africa-Nouakchott(90),
				africa-Ouagadougou(91),
				africa-PortoNovo(92),
				africa-SaoTome(93),
				africa-Timbuktu(94),
				africa-Tripoli(95),
				africa-Tunis(96),
				africa-Windhoek(97),
				america-Adak(98),
				america-Anchorage(99),
				america-Anguilla(100),
				america-Antigua(101),
				america-Araguaina(102),
				america-Aruba(103),
				america-Asuncion(104),
				america-Atikokan(105),
				america-Atka(106),
				america-Bahia(107),
				america-Barbados(108),
				america-Belem(109),
				america-Belize(110),
				america-BlancSablon(111),
				america-BoaVista(112),
				america-Bogota(113),
				america-Boise(114),
				america-BuenosAires(115),
				america-CambridgeBay(116),
				america-CampoGrande(117),
				america-Cancun(118),
				america-Caracas(119),
				america-Catamarca(120),
				america-Cayenne(121),
				america-Cayman(122),
				america-Chicago(123),
				america-Chihuahua(124),
				america-CoralHarbour(125),
				america-Cordoba(126),
				america-CostaRica(127),
				america-Cuiaba(128),
				america-Curacao(129),
				america-Danmarkshavn(130),
				america-Dawson(131),
				america-DawsonCreek(132),
				america-Denver(133),
				america-Detroit(134),
				america-Dominica(135),
				america-Edmonton(136),
				america-Eirunepe(137),
				america-ElSalvador(138),
				america-Ensenada(139),
				america-FortWayne(140),
				america-Fortaleza(141),
				america-GlaceBay(142),
				america-Godthab(143),
				america-GooseBay(144),
				america-GrandTurk(145),
				america-Grenada(146),
				america-Guadeloupe(147),
				america-Guatemala(148),
				america-Guayaquil(149),
				america-Guyana(150),
				america-Halifax(151),
				america-Havana(152),
				america-Hermosillo(153),
				america-Indianapolis(154),
				america-Inuvik(155),
				america-Iqaluit(156),
				america-Jamaica(157),
				america-Jujuy(158),
				america-Juneau(159),
				america-KnoxIN(160),
				america-LaPaz(161),
				america-Lima(162),
				america-LosAngeles(163),
				america-Louisville(164),
				america-Maceio(165),
				america-Managua(166),
				america-Manaus(167),
				america-Martinique(168),
				america-Mazatlan(169),
				america-Mendoza(170),
				america-Menominee(171),
				america-Merida(172),
				america-MexicoCity(173),
				america-Miquelon(174),
				america-Moncton(175),
				america-Monterrey(176),
				america-Montevideo(177),
				america-Montreal(178),
				america-Montserrat(179),
				america-Nassau(180),
				america-NewYork(181),
				america-Nipigon(182),
				america-Nome(183),
				america-Noronha(184),
				america-Panama(185),
				america-Pangnirtung(186),
				america-Paramaribo(187),
				america-Phoenix(188),
				america-PortAuPrince(189),
				america-PortOfSpain(190),
				america-PortoAcre(191),
				america-PortoVelho(192),
				america-PuertoRico(193),
				america-RainyRiver(194),
				america-RankinInlet(195),
				america-Recife(196),
				america-Regina(197),
				america-RioBranco(198),
				america-Rosario(199),
				america-Santiago(200),
				america-SantoDomingo(201),
				america-SaoPaulo(202),
				america-Scoresbysund(203),
				america-Shiprock(204),
				america-StJohns(205),
				america-StKitts(206),
				america-StLucia(207),
				america-StThomas(208),
				america-StVincent(209),
				america-SwiftCurrent(210),
				america-Tegucigalpa(211),
				america-Thule(212),
				america-ThunderBay(213),
				america-Tijuana(214),
				america-Toronto(215),
				america-Tortola(216),
				america-Vancouver(217),
				america-Virgin(218),
				america-Whitehorse(219),
				america-Winnipeg(220),
				america-Yakutat(221),
				america-Yellowknife(222),
				antarctica-Casey(223),
				antarctica-Davis(224),
				antarctica-DumontDUrville(225),
				antarctica-Mawson(226),
				antarctica-McMurdo(227),
				antarctica-Palmer(228),
				antarctica-Rothera(229),
				antarctica-SouthPole(230),
				antarctica-Syowa(231),
				antarctica-Vostok(232),
				arctic-Longyearbyen(233),
				asia-Aden(234),
				asia-Almaty(235),
				asia-Amman(236),
				asia-Anadyr(237),
				asia-Aqtau(238),
				asia-Aqtobe(239),
				asia-Ashgabat(240),
				asia-Ashkhabad(241),
				asia-Baghdad(242),
				asia-Bahrain(243),
				asia-Baku(244),
				asia-Bangkok(245),
				asia-Beirut(246),
				asia-Bishkek(247),
				asia-Brunei(248),
				asia-Calcutta(249),
				asia-Choibalsan(250),
				asia-Chongqing(251),
				asia-Chungking(252),
				asia-Colombo(253),
				asia-Dacca(254),
				asia-Damascus(255),
				asia-Dhaka(256),
				asia-Dili(257),
				asia-Dubai(258),
				asia-Dushanbe(259),
				asia-Gaza(260),
				asia-Harbin(261),
				asia-HongKong(262),
				asia-Hovd(263),
				asia-Irkutsk(264),
				asia-Istanbul(265),
				asia-Jakarta(266),
				asia-Jayapura(267),
				asia-Jerusalem(268),
				asia-Kabul(269),
				asia-Kamchatka(270),
				asia-Karachi(271),
				asia-Kashgar(272),
				asia-Katmandu(273),
				asia-Krasnoyarsk(274),
				asia-KualaLumpur(275),
				asia-Kuching(276),
				asia-Kuwait(277),
				asia-Macao(278),
				asia-Macau(279),
				asia-Magadan(280),
				asia-Makassar(281),
				asia-Manila(282),
				asia-Muscat(283),
				asia-Nicosia(284),
				asia-Novosibirsk(285),
				asia-Omsk(286),
				asia-Oral(287),
				asia-PhnomPenh(288),
				asia-Pontianak(289),
				asia-Pyongyang(290),
				asia-Qatar(291),
				asia-Qyzylorda(292),
				asia-Rangoon(293),
				asia-Riyadh(294),
				asia-Riyadh87(295),
				asia-Riyadh88(296),
				asia-Riyadh89(297),
				asia-Saigon(298),
				asia-Sakhalin(299),
				asia-Samarkand(300),
				asia-Seoul(301),
				asia-Shanghai(302),
				asia-Singapore(303),
				asia-Taipei(304),
				asia-Tashkent(305),
				asia-Tbilisi(306),
				asia-Tehran(307),
				asia-TelAviv(308),
				asia-Thimbu(309),
				asia-Thimphu(310),
				asia-Tokyo(311),
				asia-UjungPandang(312),
				asia-Ulaanbaatar(313),
				asia-UlanBator(314),
				asia-Urumqi(315),
				asia-Vientiane(316),
				asia-Vladivostok(317),
				asia-Yakutsk(318),
				asia-Yekaterinburg(319),
				asia-Yerevan(320),
				atlantic-Azores(321),
				atlantic-Bermuda(322),
				atlantic-Canary(323),
				atlantic-CapeVerde(324),
				atlantic-Faeroe(325),
				atlantic-JanMayen(326),
				atlantic-Madeira(327),
				atlantic-Reykjavik(328),
				atlantic-SouthGeorgia(329),
				atlantic-StHelena(330),
				atlantic-Stanley(331),
				australia-ACT(332),
				australia-Adelaide(333),
				australia-Brisbane(334),
				australia-BrokenHill(335),
				australia-Canberra(336),
				australia-Currie(337),
				australia-Darwin(338),
				australia-Hobart(339),
				australia-LHI(340),
				australia-Lindeman(341),
				australia-LordHowe(342),
				australia-Melbourne(343),
				australia-NSW(344),
				australia-North(345),
				australia-Perth(346),
				australia-Queensland(347),
				australia-South(348),
				australia-Sydney(349),
				australia-Tasmania(350),
				australia-Victoria(351),
				australia-West(352),
				australia-Yancowinna(353),
				brazil-Acre(354),
				brazil-DeNoronha(355),
				brazil-East(356),
				brazil-West(357),
				canada-Atlantic(358),
				canada-Central(359),
				canada-EastSaskatchewan(360),
				canada-Eastern(361),
				canada-Mountain(362),
				canada-Newfoundland(363),
				canada-Pacific(364),
				canada-Saskatchewan(365),
				canada-Yukon(366),
				chile-Continental(367),
				chile-EasterIsland(368),
				etc-GMT(369),
				etc-GMTE0(370),
				etc-GMTE1(371),
				etc-GMTE10(372),
				etc-GMTE11(373),
				etc-GMTE12(374),
				etc-GMTE2(375),
				etc-GMTE3(376),
				etc-GMTE4(377),
				etc-GMTE5(378),
				etc-GMTE6(379),
				etc-GMTE7(380),
				etc-GMTE8(381),
				etc-GMTE9(382),
				etc-GMTW0(383),
				etc-GMTW1(384),
				etc-GMTW10(385),
				etc-GMTW11(386),
				etc-GMTW12(387),
				etc-GMTW13(388),
				etc-GMTW14(389),
				etc-GMTW2(390),
				etc-GMTW3(391),
				etc-GMTW4(392),
				etc-GMTW5(393),
				etc-GMTW6(394),
				etc-GMTW7(395),
				etc-GMTW8(396),
				etc-GMTW9(397),
				etc-GMT0(398),
				etc-Greenwich(399),
				etc-UCT(400),
				etc-UTC(401),
				etc-Universal(402),
				etc-Zulu(403),
				europe-Amsterdam(404),
				europe-Andorra(405),
				europe-Athens(406),
				europe-Belfast(407),
				europe-Belgrade(408),
				europe-Berlin(409),
				europe-Bratislava(410),
				europe-Brussels(411),
				europe-Bucharest(412),
				europe-Budapest(413),
				europe-Chisinau(414),
				europe-Copenhagen(415),
				europe-Dublin(416),
				europe-Gibraltar(417),
				europe-Guernsey(418),
				europe-Helsinki(419),
				europe-IsleOfMan(420),
				europe-Istanbul(421),
				europe-Jersey(422),
				europe-Kaliningrad(423),
				europe-Kiev(424),
				europe-Lisbon(425),
				europe-Ljubljana(426),
				europe-London(427),
				europe-Luxembourg(428),
				europe-Madrid(429),
				europe-Malta(430),
				europe-Mariehamn(431),
				europe-Minsk(432),
				europe-Monaco(433),
				europe-Moscow(434),
				europe-Nicosia(435),
				europe-Oslo(436),
				europe-Paris(437),
				europe-Prague(438),
				europe-Riga(439),
				europe-Rome(440),
				europe-Samara(441),
				europe-SanMarino(442),
				europe-Sarajevo(443),
				europe-Simferopol(444),
				europe-Skopje(445),
				europe-Sofia(446),
				europe-Stockholm(447),
				europe-Tallinn(448),
				europe-Tirane(449),
				europe-Tiraspol(450),
				europe-Uzhgorod(451),
				europe-Vaduz(452),
				europe-Vatican(453),
				europe-Vienna(454),
				europe-Vilnius(455),
				europe-Volgograd(456),
				europe-Warsaw(457),
				europe-Zagreb(458),
				europe-Zaporozhye(459),
				europe-Zurich(460),
				indian-Antananarivo(461),
				indian-Chagos(462),
				indian-Christmas(463),
				indian-Cocos(464),
				indian-Comoro(465),
				indian-Kerguelen(466),
				indian-Mahe(467),
				indian-Maldives(468),
				indian-Mauritius(469),
				indian-Mayotte(470),
				indian-Reunion(471),
				mexico-BajaNorte(472),
				mexico-BajaSur(473),
				mexico-General(474),
				mideast-Riyadh87(475),
				mideast-Riyadh88(476),
				mideast-Riyadh89(477),
				pacific-Apia(478),
				pacific-Auckland(479),
				pacific-Chatham(480),
				pacific-Easter(481),
				pacific-Efate(482),
				pacific-Enderbury(483),
				pacific-Fakaofo(484),
				pacific-Fiji(485),
				pacific-Funafuti(486),
				pacific-Galapagos(487),
				pacific-Gambier(488),
				pacific-Guadalcanal(489),
				pacific-Guam(490),
				pacific-Honolulu(491),
				pacific-Johnston(492),
				pacific-Kiritimati(493),
				pacific-Kosrae(494),
				pacific-Kwajalein(495),
				pacific-Majuro(496),
				pacific-Marquesas(497),
				pacific-Midway(498),
				pacific-Nauru(499),
				pacific-Niue(500),
				pacific-Norfolk(501),
				pacific-Noumea(502),
				pacific-PagoPago(503),
				pacific-Palau(504),
				pacific-Pitcairn(505),
				pacific-Ponape(506),
				pacific-PortMoresby(507),
				pacific-Rarotonga(508),
				pacific-Saipan(509),
				pacific-Samoa(510),
				pacific-Tahiti(511),
				pacific-Tarawa(512),
				pacific-Tongatapu(513),
				pacific-Truk(514),
				pacific-Wake(515),
				pacific-Wallis(516),
				pacific-Yap(517),
				us-Alaska(518),
				us-Aleutian(519),
				us-Arizona(520),
				us-Central(521),
				us-EastIndiana(522),
				us-Eastern(523),
				us-Hawaii(524),
				us-IndianaStarke(525),
				us-Michigan(526),
				us-Mountain(527),
				us-Pacific(528),
				us-PacificNew(529),
				us-Samoa(530),
				america-Argentina-BuenosAires(531),
				america-Argentina-Catamarca(532),
				america-Argentina-ComodRivadavia(533),
				america-Argentina-Cordoba(534),
				america-Argentina-Jujuy(535),
				america-Argentina-LaRioja(536),
				america-Argentina-Mendoza(537),
				america-Argentina-RioGallegos(538),
				america-Argentina-SanJuan(539),
				america-Argentina-Tucuman(540),
				america-Argentina-Ushuaia(541),
				america-Indiana-Indianapolis(542),
				america-Indiana-Knox(543),
				america-Indiana-Marengo(544),
				america-Indiana-Petersburg(545),
				america-Indiana-Vevay(546),
				america-Indiana-Vincennes(547),
				america-Kentucky-Louisville(548),
				america-Kentucky-Monticello(549),
				america-NorthDakota-Center(550),
				america-NorthDakota-NewSalem(551)
		      }
	MAX-ACCESS    read-write
	STATUS	      current
	DESCRIPTION   "Timezone values. Since + is not a valid character inside enum 
		       declaration, E(ast) and W(est) are used to indicate + and - 
		       respectively. For example, etc-GMTE1 indicates Etc-GMT+1 and 
		       etc-GMTW1 indicates Etc-GMT-1."
	::= { rcUserSetTime 7 }


-- RecRecord

rcRecReservTable OBJECT-TYPE
     SYNTAX       SEQUENCE OF RcRecReservEntry
     MAX-ACCESS   not-accessible
     STATUS       current
     DESCRIPTION  "This table would display the statistics of several HW
                   record type used.  This will also let the user reserve
                   certain number of records for each type."
     ::= { rcRec 1 }

rcRecReservTablEntry OBJECT-TYPE
        SYNTAX        RcRecReservEntry
        MAX-ACCESS    not-accessible
        STATUS        current
        DESCRIPTION   ""
        INDEX         { rcRecReservRecordType }
        ::= { rcRecReservTable 1 }

RcRecReservEntry ::=
     SEQUENCE {
             rcRecReservRecordType      INTEGER,
             rcRecReservUsed            Integer32,
             rcRecReservReserved        Integer32,
             rcRecReservNewReserved     Integer32,
             rcRecReservDefReserved     Integer32
     }

rcRecReservRecordType OBJECT-TYPE
     SYNTAX         INTEGER  {
                          filter(1),
                          ipmc(2),
                          local(3),
                          mac(4),
                          static(5),
                          vrrp(6)
                      }
     MAX-ACCESS     read-only
     STATUS         current
     DESCRIPTION    "."
     ::= { rcRecReservTablEntry 1 }

rcRecReservUsed OBJECT-TYPE
     SYNTAX         Integer32
     MAX-ACCESS     read-only
     STATUS         current
     DESCRIPTION    "Displayes the number of HW records actually usee
                     by the recordType."
     ::= { rcRecReservTablEntry 2 }

rcRecReservReserved OBJECT-TYPE
     SYNTAX         Integer32
     MAX-ACCESS     read-only
     STATUS         current
     DESCRIPTION    "Displayes the number of HW records reserved for
                     the recordType."
     ::= { rcRecReservTablEntry 3 }

rcRecReservNewReserved OBJECT-TYPE
     SYNTAX         Integer32
     MAX-ACCESS     read-write
     STATUS         current
     DESCRIPTION    "Displayes the number of HW records that w ill
                     be reserved for this recordType after reset if the
                     configuration is saved."
     ::= { rcRecReservTablEntry 4 }

rcRecReservDefReserved OBJECT-TYPE
     SYNTAX         Integer32
     MAX-ACCESS     read-only
     STATUS         current
     DESCRIPTION    "Number of records reserved for this recordType
                     if loaded with factory default."
     ::= { rcRecReservTablEntry 5 }

-- SSH Group
-- SSH Global Information. All requires RWA access.

rcSshGlobal   OBJECT IDENTIFIER        ::= { rcSsh 1 }

rcSshGlobalVersion OBJECT-TYPE
     SYNTAX       INTEGER {
                         v2only(1),
                         both(2)
                      }
     MAX-ACCESS   read-write
     STATUS       current
     DESCRIPTION  "SSH version"
     DEFVAL       { v2only }
     ::= { rcSshGlobal 1 }

rcSshGlobalPort OBJECT-TYPE
     SYNTAX       Integer32
     MAX-ACCESS   read-write
     STATUS       current
     DESCRIPTION  "SSH connection port."
     DEFVAL       { 22 }
     ::= { rcSshGlobal 2 }

rcSshGlobalMaxSession OBJECT-TYPE
     SYNTAX       Integer32 (0..8)
     MAX-ACCESS   read-write
     STATUS       current
     DESCRIPTION  "Number of session allowed."
     DEFVAL       { 4 }
     ::= { rcSshGlobal 3 }

rcSshGlobalTimeout OBJECT-TYPE
     SYNTAX       Integer32 (1..120)
     MAX-ACCESS   read-write
     STATUS       current
     DESCRIPTION  "SSH connection timeout in seconds."
     DEFVAL       { 60 }
     ::= { rcSshGlobal 4 }

rcSshGlobalRsaKeySize OBJECT-TYPE
     SYNTAX       Integer32 (0|512..2048)
     MAX-ACCESS   read-write
     STATUS       current
     DESCRIPTION  "SSH Rsa key size."
     DEFVAL       { 1024 }
     ::= { rcSshGlobal 5 }

rcSshGlobalDsaKeySize OBJECT-TYPE
     SYNTAX       INTEGER(1024)
     MAX-ACCESS   read-write
     STATUS       current
     DESCRIPTION  "SSH Dsa key size."
     DEFVAL       { 1024 }
     ::= { rcSshGlobal 6 }

rcSshGlobalRsaAuth OBJECT-TYPE
     SYNTAX       TruthValue
     MAX-ACCESS   read-write
     STATUS       current
     DESCRIPTION  "Enable/disable SSH RSA authentication"
     DEFVAL       { true }
     ::= { rcSshGlobal 7 }

rcSshGlobalDsaAuth OBJECT-TYPE
     SYNTAX       TruthValue
     MAX-ACCESS   read-write
     STATUS       current
     DESCRIPTION  "Enable/disable SSH DSA authentication"
     DEFVAL       { true }
     ::= { rcSshGlobal 8 }

rcSshGlobalPassAuth OBJECT-TYPE
     SYNTAX       TruthValue
     MAX-ACCESS   read-write
     STATUS       current
     DESCRIPTION  "Enable/disable SSH RSA authentication"
     DEFVAL       { true }
     ::= { rcSshGlobal 9 }

rcSshGlobalKeyAction OBJECT-TYPE
     SYNTAX       INTEGER  {
                         none(0),
                         generateDsa(1),
                         generateRsa(2),
                         deleteDsa(3),
                         deleteRsa(4)
                      }
     MAX-ACCESS   read-write
     STATUS       current
     DESCRIPTION  "SSH key action."
     ::= { rcSshGlobal 10 }

rcSshGlobalEnable OBJECT-TYPE
     SYNTAX       INTEGER {
                         false(0),
                         true(1),
                         secure(2)
                      }
     MAX-ACCESS   read-write
     STATUS       current
     DESCRIPTION  "Enable/disable, or securely enable SSH. Securely enable
                   turns off other daemon flag, and it takes ffect afte reboot"
     DEFVAL       { false }
     ::= { rcSshGlobal 11 }

rcSshGlobalHostIpAddr OBJECT-TYPE
     SYNTAX       IpAddress
     MAX-ACCESS   read-write
     STATUS       current
     DESCRIPTION  "current remote ip addr"
     ::= { rcSshGlobal 12 }

rcSshGlobalRetries OBJECT-TYPE
     SYNTAX       Integer32 (1..100)
     MAX-ACCESS   read-write
     STATUS       current
     DESCRIPTION  "Number of SSH retries allowed."
     DEFVAL       { 3 }
     ::= { rcSshGlobal 13 }

rcSshGlobalDsaAuthKeyName OBJECT-TYPE
     SYNTAX      DisplayString (SIZE (0..128))
     MAX-ACCESS  read-only
     STATUS      current
     DESCRIPTION "Name of the DSA Auth Key. When not used, the value is a zero
                  length string."
     ::=  { rcSshGlobal 14 }

rcSshGlobalRsaAuthKeyName OBJECT-TYPE
     SYNTAX      DisplayString (SIZE (0..128))
     MAX-ACCESS  read-only
     STATUS      current
     DESCRIPTION "Name of the RSA Auth Key. When not used, the value is a zero
                  length string."
     ::=  { rcSshGlobal 15 }

rcSshGlobalRekeyEnable OBJECT-TYPE
     SYNTAX       TruthValue
     MAX-ACCESS   read-write
     STATUS       current
     DESCRIPTION  "Enable/disable SSH Rekey. This needs global SSH flag to be 
                   enabled"
     DEFVAL       { false }
     ::= { rcSshGlobal 16 }

rcSshGlobalRekeyTimeInterval OBJECT-TYPE
     SYNTAX       Integer32 (1..6)
     UNITS        "hours"
     MAX-ACCESS   read-write
     STATUS       current
     DESCRIPTION  "Time interval in hours after which active SSH sessions
                   should start the rekey process."
     DEFVAL       { 1 }
     ::= { rcSshGlobal 17 }

rcSshGlobalRekeyDataLimit OBJECT-TYPE
     SYNTAX       Integer32 (1..6)
     MAX-ACCESS   read-write
     STATUS       current
     DESCRIPTION  "Total data(in GB) Tx and Rx in active SSH sessions 
                   after which sessions should start the rekey process."
     DEFVAL       { 1 }
     ::= { rcSshGlobal 18 }
 
rcSshGlobalSftpEnable OBJECT-TYPE
     SYNTAX       TruthValue
     MAX-ACCESS   read-write
     STATUS       current
     DESCRIPTION  "Enable/disable SSH Sftp."
     DEFVAL       { true }
     ::= { rcSshGlobal 19 }

rcSshGlobalKeyboardInteractiveAuth OBJECT-TYPE
     SYNTAX       TruthValue
     MAX-ACCESS   read-write
     STATUS       current
     DESCRIPTION  "Enable/disable SSH keyboard-interactive mode authentication"
     DEFVAL       { false }
     ::= { rcSshGlobal 20 } 

rcSshAuthType  OBJECT-TYPE
     SYNTAX         BITS
		    {
			   hmacSha1(0),
			   aeadAes128GcmSsh(1),
			   aeadAes256GcmSsh(2)
		    }
     MAX-ACCESS     read-write
     STATUS         current
     DESCRIPTION    "value is one of multiple (logically by 'OR' of
                    following value:
                        bit 0 - hmac_sha1
                        bit 1 - aead_aes_128_gcm_ssh
                        bit 2 - aead_aes_256_gcm_ssh
                    hmac_sha1            : Enables hmac-sha1 auth type
                    aead_aes_128_gcm_ssh : Enables aead-aes-128-gcm-ssh auth
                                           type
                    aead_aes_256_gcm_ssh : Enables aead-aes-256-gcm-ssh auth
                                           type"
    ::= { rcSshGlobal  21 }

rcSshEncryptionType  OBJECT-TYPE
     SYNTAX         BITS
		    {
			   aes128Cbc(0),
			   aes256Cbc(1),
			   threeDesCbc(2),
			   aeadAes128GcmSsh(3),
			   aeadAes256GcmSsh(4),
			   aes128Ctr(5),
			   rijndael128Cbc(6),
			   aes256Ctr(7),
			   aes192Ctr(8),
			   aes192Cbc(9),
			   rijndael192Cbc(10),
			   blowfishCbc(11)
		    }
     MAX-ACCESS     read-write
     STATUS         current
     DESCRIPTION    "value is one of multiple (logically by 'OR' of
                    following value:
                        bit 0 - aes128_cbc
                        bit 1 - aes256_cbc
                        bit 2 - 3des_cbc
                        bit 3 - aead_aes_128_gcm_ssh
                        bit 4 - aead_aes_256_gcm_ssh
                        bit 5 - aes128_ctr
                        bit 6 - rijndael128_cbc
                        bit 7 - aes256_ctr
                        bit 8 - aes192_ctr
                        bit 9 - aes192_cbc
                        bit 10 - rijndael192_cbc
                        bit 11 - blowfish_cbc
                    aes128_cbc             : Enables hmac-sha1 encryption type
                    aes256_cbc             : Enables aes256-cbc encrytption
                                             type
                    3des_cbc               : Enables 3des-cbc type
                    aead_aes_128_gcm_ssh   : Enables aead-aes-128-gcm-ssh
                                             encryption type
                    aead_aes_256_gcm_ssh   : Enables  aead-aes-256-gcm-ssh
                                             type
                    aes128_ctr             : Enables  aes128-ctr auth type
                    rijndael128_cbc        : Enables rijndael128-cbc
                                             encryption type
                    aes256_ctr             : Enables aes256-ctr encrytipn
                                             type
                    aes192_ctr             : Enables aes198-ctr encryption
                                             type
                    aes192_cbc             : Enables aes192-cbc type
                    rijndael192_cbc        : Enables rijndael192-cbc
                                             encryption type
                    blowfish_cbc           : Enables  blowfish-cbc type"
     ::= { rcSshGlobal  22 }

rcSshKeyExchangeMethod  OBJECT-TYPE
     SYNTAX         BITS
		    {
			   diffieHellmanGroup14Sha1(0),
			   diffieHellmanGroup1Sha1(1)
		    }
     MAX-ACCESS     read-write
     STATUS         current
     DESCRIPTION    "value is one of multiple (logically by 'OR'
                    of following value:
                          bit 0 - diffie_hellman_group14_sha1
                          bit 1 - diffie_hellman_group1_sha1
                    diffie_hellman_group14_sha1 : Enables 
                                        diffie-hellman-group14-sha1 method
                    diffie_hellman_group1_sha1  : Enables
                                        diffie_hellman_group1_sha1 method"
     ::= { rcSshGlobal  23 }

rcSshGlobalClientEnable OBJECT-TYPE
     SYNTAX       TruthValue
     MAX-ACCESS   read-write
     STATUS       current
     DESCRIPTION  "Enable/disable SSH Client."
     DEFVAL       { true }
     ::= { rcSshGlobal 24 }

 
rcSslMipTable OBJECT-TYPE
     SYNTAX       SEQUENCE OF RcSslMipEntry
     MAX-ACCESS   not-accessible
     STATUS       current
     DESCRIPTION  "This table would display the MIP of the SSL blade
                   according to the slot number."
     ::= { rcSsh 2 }

rcSslMipTableEntry OBJECT-TYPE
        SYNTAX        RcSslMipEntry
        MAX-ACCESS    not-accessible
        STATUS        current
        DESCRIPTION   "This table get the MIP of the SSL blade on which
                       the blade is in different cluster."
        INDEX         { rcSslMipSlot }
        ::= { rcSslMipTable 1 }

RcSslMipEntry ::=
     SEQUENCE {
             rcSslMipSlot      Integer32,
             rcSslMipMip       DisplayString
     }

rcSslMipSlot OBJECT-TYPE
     SYNTAX         Integer32 (0..2147483647)
     MAX-ACCESS     read-only
     STATUS         current
     DESCRIPTION    "Used as an index to find out the MIP of SSL blade."
     ::= { rcSslMipTableEntry 1 }

rcSslMipMip OBJECT-TYPE
     SYNTAX         DisplayString
     MAX-ACCESS     read-only
     STATUS         current
     DESCRIPTION    "Master IP of the SSL blade."
     ::= { rcSslMipTableEntry 2 }

-- SSHC Group
-- SSHC Global Information.

rcSshcGlobal   OBJECT IDENTIFIER        ::= { rcSsh 3 }

rcSshcGlobalActiveSessions OBJECT-TYPE
      SYNTAX       INTEGER (0..16)
      MAX-ACCESS   read-only
      STATUS       deprecated
      DESCRIPTION  "Number of SSHC active sessions"
      DEFVAL       { 0 }
      ::= { rcSshcGlobal 1 }

rcSshcGlobalPort OBJECT-TYPE
      SYNTAX       Integer32 (1..65535)
      MAX-ACCESS   read-write
      STATUS       current
      DESCRIPTION  "SSHC connection port."
      DEFVAL       { 22 }
      ::= { rcSshcGlobal 2 }

rcSshcGlobalAuthenticationTimeout OBJECT-TYPE
      SYNTAX       INTEGER (1..120)
      MAX-ACCESS   read-write
      STATUS       deprecated
      DESCRIPTION  "Authentication timeout in seconds."
      DEFVAL       { 30 }
      ::= { rcSshcGlobal 3 }

rcSshcGlobalDsaAuthentication OBJECT-TYPE
      SYNTAX       TruthValue
      MAX-ACCESS   read-write
      STATUS       current
      DESCRIPTION  "Authentication using DSA."
      DEFVAL       { true }
      ::= { rcSshcGlobal 4 }

rcSshcGlobalPasswordAuthentication OBJECT-TYPE
      SYNTAX       TruthValue
      MAX-ACCESS   read-write
      STATUS       current
      DESCRIPTION  "Authentication using password."
      DEFVAL       { false }
      ::= { rcSshcGlobal 5 }

rcSshcGlobalUserName OBJECT-TYPE
      SYNTAX       DisplayString (SIZE (0..30))
      MAX-ACCESS   read-write
      STATUS       current
      DESCRIPTION  "User name."
      ::= { rcSshcGlobal 6 }

rcSshcGlobalSftpServerAddress OBJECT-TYPE
      SYNTAX       IpAddress
      MAX-ACCESS   read-write
      STATUS       deprecated
      DESCRIPTION  "SFTP server IPv4 address."
      ::= { rcSshcGlobal 7 }

rcSshcGlobalDsaKeySize OBJECT-TYPE
      SYNTAX       Integer32 (0|512..1024)
      MAX-ACCESS   read-write
      STATUS       current
      DESCRIPTION  "Size of the SSH Client DSA key. Must be a multiple of 64."
      DEFVAL       { 512 }
      ::= { rcSshcGlobal 8 }

rcSshcGlobalRsaKeySize OBJECT-TYPE
     SYNTAX       Integer32 (0|1024..2048)
     MAX-ACCESS   read-write
     STATUS       current
     DESCRIPTION  "SSH Client RSA key size. Must be a multiple of 128."
     DEFVAL       { 1024 }
     ::= { rcSshcGlobal 9 }

rcSshcGlobalRsaAuth OBJECT-TYPE
     SYNTAX       TruthValue
     MAX-ACCESS   read-write
     STATUS       deprecated
     DESCRIPTION  "Enable/disable SSH Client RSA authentication"
     DEFVAL       { true }
     ::= { rcSshcGlobal 10 }

rcSshcGlobalDsaAuth OBJECT-TYPE
     SYNTAX       TruthValue
     MAX-ACCESS   read-write
     STATUS       deprecated
     DESCRIPTION  "Enable/disable SSH Client DSA authentication"
     DEFVAL       { true }
     ::= { rcSshcGlobal 11 }

rcSshcGlobalPassAuth OBJECT-TYPE
     SYNTAX       TruthValue
     MAX-ACCESS   read-write
     STATUS       deprecated
     DESCRIPTION  "Enable/disable SSH Client password authentication"
     DEFVAL       { true }
     ::= { rcSshcGlobal 12 }

rcSshcGlobalKeyAction OBJECT-TYPE
     SYNTAX       INTEGER  {
                         none(0),
                         generateDsa(1),
                         generateRsa(2),
                         deleteDsa(3),
                         deleteRsa(4),
                         generateDsaForce(5),
                         generateRsaForce(6)
                      }
     MAX-ACCESS   read-write
     STATUS       current
     DESCRIPTION  "SSH Client key action. The actions generateDsa(1) and 
                   generateRsa(2) initiate the generation of the DSA key
                   or RSA key if the key is not already generated. deleteDsa(3)
                   and deleteRsa(4) actions delete the respective DSA or RSA key 
                   if one was generated.
                   To generate a new key overwriting an existing key
                   generateDsaForce(5) or generateRsaForce(6) must be used."
     ::= { rcSshcGlobal 13 }

rcSshcGlobalDsaHostKeyStatus OBJECT-TYPE
       SYNTAX      INTEGER {
                       notGenerated(1),
                       generated(2),
                       generating(3)
                   }
       MAX-ACCESS  read-only
       STATUS      current
       DESCRIPTION "This object indicates the current status of the SSH
                    DSA host key.  If the DSA host key has not yet been
                    generated, the value will be notGenerated(1).  If it
                    has already been generated, the value will be
                    generated(2).  If it is currently being generated,
                    the value will be generating(3)."
       ::= { rcSshcGlobal 14 }

rcSshcGlobalRsaHostKeyStatus OBJECT-TYPE
       SYNTAX      INTEGER {
                       notGenerated(1),
                       generated(2),
                       generating(3)
                   }
       MAX-ACCESS  read-only
       STATUS      current
       DESCRIPTION "This object indicates the current status of the SSH
                    RSA host key.  If the RSA host key has not yet been
                    generated, the value will be notGenerated(1).  If it
                    has already been generated, the value will be
                    generated(2).  If it is currently being generated,
                    the value will be generating(3)."
       ::= { rcSshcGlobal 15 }

rcSshcGlobalTftpAction OBJECT-TYPE
       SYNTAX      INTEGER {
                       none(1),
                       uploadSshcDsaAuthKey(2),
                       uploadSshcRsaAuthKey(3)
                   }
       MAX-ACCESS  read-write
       STATUS      current
       DESCRIPTION "This object may be set to initiate a TFTP upload of
                    SSH Client public keys.  When retrieved, the value will alwa
ys
                    be none(1)."
       ::= { rcSshcGlobal 16 }

rcSshcGlobalUsbAction OBJECT-TYPE
       SYNTAX      INTEGER {
                       none(1),
                       uploadSshcDsaAuthKey(2),
                       uploadSshcRsaAuthKey(3)
                   }
       MAX-ACCESS  read-write
       STATUS      current
       DESCRIPTION "This object may be set to initiate a USB upload of
                    SSH Client public keys.  When retrieved, the value will alwa
ys
                    be none(1)."
       ::= { rcSshcGlobal 17 }

rcSshcGlobalKeyFileName OBJECT-TYPE
        SYNTAX  DisplayString (SIZE (0..128))
        MAX-ACCESS      read-write
        STATUS  current
        DESCRIPTION "Name of the key file on the TFTP server or USB where the key is uploaded"
        ::= { rcSshcGlobal 18 }

rcSshcGlobalRsaAuthenthication OBJECT-TYPE
     SYNTAX       TruthValue
     MAX-ACCESS   read-write
     STATUS       current
     DESCRIPTION  "Set to true to use RSA authentication to the SFTP server. When toggling the 
                   value from true to false the default authentication method (DSA key) will 
                   be activated"
     DEFVAL       { false }
     ::= { rcSshcGlobal 19 }  

rcSshcGlobalSftpServerPassword OBJECT-TYPE
     SYNTAX       DisplayString (SIZE (0..30))
     MAX-ACCESS   read-write
     STATUS       current
     DESCRIPTION  "The password used for SFTP authentication"
     ::= { rcSshcGlobal 20 }  

rcSshcGlobalSftpServerInetAddressType OBJECT-TYPE
      SYNTAX       InetAddressType
      MAX-ACCESS   read-write
      STATUS       current
      DESCRIPTION  "SFTP server IP address type."
      ::= { rcSshcGlobal 21 }

rcSshcGlobalSftpServerInetAddress OBJECT-TYPE
      SYNTAX       InetAddress
      MAX-ACCESS   read-write
      STATUS       current
      DESCRIPTION  "SFTP server IP address."
      ::= { rcSshcGlobal 22 }

rcSshcGlobalRekeyDataLimit OBJECT-TYPE
     SYNTAX       Integer32 (1..6)
     MAX-ACCESS   read-write
     STATUS       current
     DESCRIPTION  "Total data(in GB) Tx and Rx in active SSH Client sessions 
                   after which sessions will start the rekey process."
     DEFVAL       { 1 }
     ::= { rcSshcGlobal 23 }

-- LACP Group
-- LACP Global Information. 

rcLacpGlobal   OBJECT IDENTIFIER        ::= { rcLacp 1 }

rcLacpGlobalEnable OBJECT-TYPE
     SYNTAX       TruthValue 
     MAX-ACCESS   read-write
     STATUS       current
     DESCRIPTION  "globally enable/disable LACP"
     DEFVAL       { false }
     ::= { rcLacpGlobal 1 }

rcLacpGlobalSystemPriority OBJECT-TYPE
     SYNTAX       Integer32
     MAX-ACCESS   read-write
     STATUS       current
     DESCRIPTION  "set system priority to all the LACP enabled aggregators 
                   and prots"
     DEFVAL       { 32768 }
     ::= { rcLacpGlobal 2 }

rcLacpGlobalFastPeriodicTime OBJECT-TYPE
     SYNTAX       Integer32
     MAX-ACCESS   read-write
     STATUS       current
     DESCRIPTION  "The number of milliseconds between periodic
                   transmissions using Short Timeouts. Set this
                   value to all LACP enabled ports."
     DEFVAL       { 1000 }
     ::= { rcLacpGlobal 3 }

rcLacpGlobalSlowPeriodicTime OBJECT-TYPE
     SYNTAX       Integer32
     MAX-ACCESS   read-write
     STATUS       current
     DESCRIPTION  "The number of milliseconds between periodic
                   transmissions using LONG Timeouts. Set this
                   value to all LACP enabled ports."
     DEFVAL       { 30000 }
     ::= { rcLacpGlobal 4 }

rcLacpGlobalTimeoutScale OBJECT-TYPE
     SYNTAX       Integer32
     MAX-ACCESS   read-write
     STATUS       current
     DESCRIPTION  "Scalar value used to calculate timeout time from
                   periodic time. Set this value to all LACP enabled ports."
     DEFVAL       { 3 }
     ::= { rcLacpGlobal 5 }

rcLacpGlobalAggrWaitTime OBJECT-TYPE
        SYNTAX        Integer32 (200..2000)
        MAX-ACCESS    read-write
        STATUS        current
        DESCRIPTION   "The number of mili seconds to delay aggregation
                       to allow multiple links to aggregate simultaneously."
        DEFVAL        { 2000 }
        ::= { rcLacpGlobal 6 }

rcLacpGlobalVlacpEnable OBJECT-TYPE
     SYNTAX       TruthValue
     MAX-ACCESS   read-write
     STATUS       current
     DESCRIPTION  "globally enable/disable Virtual LACP"
     DEFVAL       { false }
     ::= { rcLacpGlobal 7 }

rcLacpGlobalVlacpMulticastMACAddress OBJECT-TYPE
     SYNTAX       MacAddress
     MAX-ACCESS   read-write
     STATUS       current
     DESCRIPTION  "Virtual LACP multicast MAC address"
     ::= { rcLacpGlobal 8 }

rcLacpGlobalFastPeriodicTimeOper OBJECT-TYPE
        SYNTAX       Integer32 (10..20000) 
        MAX-ACCESS    read-only
        STATUS        current
        DESCRIPTION   "The operating value of global fast periodic timer."
        ::= { rcLacpGlobal 9 }

rcLacpGlobalSlowPeriodicTimeOper OBJECT-TYPE
        SYNTAX        Integer32 (10..30000) 
        MAX-ACCESS    read-only
        STATUS        current
        DESCRIPTION   "The operating value of global show periodic time."
        ::= { rcLacpGlobal 10 }

rcLacpGlobalTimeoutScaleOper OBJECT-TYPE
        SYNTAX        Integer32 (1..10) 
        MAX-ACCESS    read-only
        STATUS        current
        DESCRIPTION   "The operating value of global timeout scale."
        ::= { rcLacpGlobal 11 }

rcLacpGlobalAggrWaitTimeOper OBJECT-TYPE
        SYNTAX        Integer32 (10..2000) 
        MAX-ACCESS    read-only
        STATUS        current
        DESCRIPTION   "The operating value of global aggregate wait time."
        ::= { rcLacpGlobal 12 }

rcLacpGlobalSmltSysId OBJECT-TYPE
        SYNTAX       MacAddress
        MAX-ACCESS   read-write
        STATUS       current
        DESCRIPTION  "LACP system ID for SMLT"
        ::= { rcLacpGlobal 13 }

rcLacpGlobalSystemMac OBJECT-TYPE
        SYNTAX       MacAddress
        MAX-ACCESS   read-write
        STATUS       current
        DESCRIPTION  "LACP system MAC."
        ::= { rcLacpGlobal 14 }

rcLacpGlobalVlacpHoldTime OBJECT-TYPE
     SYNTAX       Integer32 (0..60)
     MAX-ACCESS   read-write
     STATUS       current
     DESCRIPTION  "Virtual LACP hold time"
     ::= { rcLacpGlobal 15 }

rcLacpGlobalVlacpSeqNumEnable OBJECT-TYPE
     SYNTAX       TruthValue
     MAX-ACCESS   read-write
     STATUS       current
     DESCRIPTION  "globally enable/disable Virtual LACP Sequence Number"
     DEFVAL       { true }
     ::= { rcLacpGlobal 16 }

rcLacpGlobalSysId OBJECT-TYPE
     SYNTAX       MacAddress
     MAX-ACCESS   read-only
     STATUS       current
     DESCRIPTION  "LACP system ID "
     ::= { rcLacpGlobal 17 }

-- rcVlacpPeerMacAddressTable  

rcVlacpPeerMacAddressTable  OBJECT-TYPE
	SYNTAX        SEQUENCE OF RcVlacpPeerMacAddressEntry
    	MAX-ACCESS    not-accessible
	STATUS        current
    	DESCRIPTION   " Virtual LACP Peer Mac Address table"
        ::= { rcLacp 2 }

rcVlacpPeerMacAddressEntry OBJECT-TYPE
    	SYNTAX        RcVlacpPeerMacAddressEntry
	MAX-ACCESS    not-accessible
    	STATUS        current
    	DESCRIPTION   "Entry containing info. for a particular peer"
    	INDEX         { rcVlacpPeerMacAddressMAC }
       	::= { rcVlacpPeerMacAddressTable 1 }

RcVlacpPeerMacAddressEntry ::= SEQUENCE {
     	rcVlacpPeerMacAddressMAC               MacAddress,
     	rcVlacpPeerMacAddressMltId             Integer32,
     	rcVlacpPeerMacAddressPort              InterfaceIndex,
	rcVlacpPeerMacAddressIpAddr            IpAddress,
     	rcVlacpPeerMacAddressRowStatus         RowStatus
     	}

rcVlacpPeerMacAddressMAC OBJECT-TYPE
    	SYNTAX        MacAddress
	MAX-ACCESS    not-accessible
    	STATUS        current
    	DESCRIPTION   "Virtual LACP peer mac address on a port/MLT"
     	::= { rcVlacpPeerMacAddressEntry 1 }

rcVlacpPeerMacAddressMltId OBJECT-TYPE
    	SYNTAX        Integer32 (1..32)
    	MAX-ACCESS    read-create
    	STATUS        current
    	DESCRIPTION   "MLT Id on which Virtual LACP peer mac address is 
  	               directly or indirectly connected"
     	::= { rcVlacpPeerMacAddressEntry 2 }

rcVlacpPeerMacAddressPort OBJECT-TYPE
    	SYNTAX        InterfaceIndex
    	MAX-ACCESS    read-create
    	STATUS        current
    	DESCRIPTION   "Ports on which Virtual LACP peer mac address is 
                       directly or indirectly connected"
        ::= { rcVlacpPeerMacAddressEntry 3 }

rcVlacpPeerMacAddressIpAddr OBJECT-TYPE
    	SYNTAX        IpAddress
    	MAX-ACCESS    read-create
    	STATUS        current
    	DESCRIPTION   "Virtual LACP peer Ip Address on port/MLT"
       	::= { rcVlacpPeerMacAddressEntry 4 }

rcVlacpPeerMacAddressRowStatus OBJECT-TYPE
    	SYNTAX        RowStatus
    	MAX-ACCESS    read-create
    	STATUS        current
    	DESCRIPTION   "Used to create/delete entries in the peer address table"
        ::= { rcVlacpPeerMacAddressEntry 5 }

rcVlacpGlobal   OBJECT IDENTIFIER        ::= { rcLacp 3 }

rcVlacpGlobalEnable OBJECT-TYPE
        SYNTAX       TruthValue
        MAX-ACCESS   read-write
        STATUS       current
        DESCRIPTION  "Globally enable/disable VLACP. This MIB object is replacing 
                      rcLacpGlobalVlacpEnable for 8600."
        DEFVAL       { false }
        ::= { rcVlacpGlobal 1 }

rcVlacpGlobalFastPeriodicTime OBJECT-TYPE
        SYNTAX       Integer32 (10..20000)
        MAX-ACCESS   read-write
        STATUS       current
        DESCRIPTION  "The number of milliseconds between periodic transmissions
                      using Short Timeouts."
        DEFVAL       { 200 }
        ::= { rcVlacpGlobal 2 }

rcVlacpGlobalSlowPeriodicTime OBJECT-TYPE
        SYNTAX       Integer32 (10000..30000)
        MAX-ACCESS   read-write
        STATUS       current
        DESCRIPTION  "The number of milliseconds between periodic transmissions
                      using LONG Timeouts." 
        DEFVAL       { 30000 }
        ::= { rcVlacpGlobal 3 }

rcVlacpGlobalTimeout OBJECT-TYPE
        SYNTAX        INTEGER {
                             short(1),
                             long(2)
                      }
        MAX-ACCESS    read-write
        STATUS        current
        DESCRIPTION   "Sets the VLACP Global timeout value."
        DEFVAL       { long }
        ::= { rcVlacpGlobal 4 }

rcVlacpGlobalTimeoutScale OBJECT-TYPE
        SYNTAX       Integer32 (2..10)
        MAX-ACCESS   read-write
        STATUS       current
        DESCRIPTION  "Scalar value used to calculate timeout time from
                      periodic time."
        DEFVAL       { 3 }
        ::= { rcVlacpGlobal 5 }
 
rcVlacpGlobalMacAddress OBJECT-TYPE
        SYNTAX         MacAddress
        MAX-ACCESS     read-write
        STATUS         current
        DESCRIPTION    "Multicast Mac Address exclusively used for VLACP Pdus."
        ::= { rcVlacpGlobal 6 }
 
rcVlacpApplyGlobalToPort OBJECT-TYPE
        SYNTAX        TruthValue
        MAX-ACCESS    read-write
        STATUS        current
        DESCRIPTION   "Applies Global values to port parameters when true."
        DEFVAL       { false }
        ::= { rcVlacpGlobal 7 }

-- rcLacpKeyTable

rcLacpKeyTable OBJECT-TYPE
    SYNTAX        SEQUENCE OF RcLacpKeyEntry
    MAX-ACCESS    not-accessible
    STATUS        current
    DESCRIPTION   "Table of settings associated with specific LACP keys."
    ::= { rcLacp 4 }

rcLacpKeyEntry OBJECT-TYPE
    SYNTAX        RcLacpKeyEntry
    MAX-ACCESS    not-accessible
    STATUS        current
    DESCRIPTION   "Entry containing data associated with a specific LACP key."
    INDEX         { rcLacpKeyValue }
    ::= { rcLacpKeyTable 1 }

RcLacpKeyEntry ::= SEQUENCE {
    rcLacpKeyValue     Unsigned32,
    rcLacpKeyRowStatus RowStatus,
    rcLacpKeyMltId     Unsigned32,
    rcLacpKeySmltId    Unsigned32
}

rcLacpKeyValue OBJECT-TYPE
    SYNTAX        Unsigned32 (0..65535)
    MAX-ACCESS    not-accessible
    STATUS        current
    DESCRIPTION
        "LACP key value to which settings are associated."
    ::= { rcLacpKeyEntry 1 }

rcLacpKeyRowStatus OBJECT-TYPE
    SYNTAX        RowStatus
    MAX-ACCESS    read-create
    STATUS        current
    DESCRIPTION
        "Used to create/delete entries in the lacp key table"
    ::= { rcLacpKeyEntry 2 }

rcLacpKeyMltId OBJECT-TYPE
    SYNTAX        Unsigned32 (0..256)
    MAX-ACCESS    read-create
    STATUS        current
    DESCRIPTION
        "MLT Id associated with this key value."
    ::= { rcLacpKeyEntry 3 }

rcLacpKeySmltId OBJECT-TYPE
    SYNTAX        Unsigned32 (0..512)
    MAX-ACCESS    read-create
    STATUS        current
    DESCRIPTION
        "SMLT Id associated with this key value."
    ::= { rcLacpKeyEntry 4 }

-- LacpMismatch Information.

rcLacpNotificationObjects   OBJECT IDENTIFIER ::=  { rcLacp 5 }

rcLacpMisconfigType  OBJECT-TYPE
        SYNTAX       INTEGER {
                         globalLacpDisable(1),
                         portLevelLacpDisable(2),
                         globalAndPortLacpDisable(3)
                     }
        MAX-ACCESS   accessible-for-notify
        STATUS       current
        DESCRIPTION  "This indicates the reason for Lacp Misconfig trap.
                      Used by rcnLacpMisconfigTrap trap."
        ::= { rcLacpNotificationObjects 1 }

-- End of LacpMismatch Information.
-- rcCLiCustom
rcCliSystemMib   OBJECT IDENTIFIER ::= { rcCliSystem 1 }
rcCliSystemObjects   OBJECT IDENTIFIER ::= { rcCliSystemMib 1 }
rcCliCustom   OBJECT IDENTIFIER ::= { rcCliSystemObjects 1 }

rcCliCustomBannerText  OBJECT-TYPE
         SYNTAX         OCTET STRING (SIZE (0..1896))
         MAX-ACCESS     read-only
         STATUS         current
         DESCRIPTION    "CLI customer banner. if object rcCliCustomBannerEnable
	 		is not true, the customer banner will not be shown on
			CLI session" 
         ::= { rcCliCustom 1 }
	 
rcCliCustomBannerEnable  OBJECT-TYPE
         SYNTAX         TruthValue
         MAX-ACCESS     read-only
         STATUS         current
         DESCRIPTION    "Indicates wthether  the customer banner rcCliCustomBannerText is
	                  shown on the CLI session"
         ::= { rcCliCustom 2 }	
    
rcLldpEnable  OBJECT-TYPE
        SYNTAX       TruthValue
        MAX-ACCESS   read-write
        STATUS       current
        DESCRIPTION  "This object controls the LLDP protocol.
                      It is used to enable/disable LLDP protocol."
	DEFVAL       { false }
        ::= { rcLldp 1 }

--
-- LLDP and CDP definition
--
rcLldpMIBObjects  OBJECT IDENTIFIER ::= { rcLldpExt 1 }
rcLldpGlobal      OBJECT IDENTIFIER ::= { rcLldpMIBObjects 1 }
rcLldpPort        OBJECT IDENTIFIER ::= { rcLldpMIBObjects 2 }

    
-- CDP port Table

rcLldpPortCdpConfigTable OBJECT-TYPE
    SYNTAX     SEQUENCE OF RcLldpPortCdpConfigEntry
    MAX-ACCESS not-accessible
    STATUS     current
    DESCRIPTION "The table contains the configuration of CDP
	         on the device's interfaces."
    ::= { rcLldpPort 1 }

rcLldpPortCdpConfigEntry OBJECT-TYPE
    SYNTAX     RcLldpPortCdpConfigEntry
    MAX-ACCESS not-accessible
    STATUS     current
    DESCRIPTION
            "An entry in the rcLldpPortCdpConfigTable,
            containing the status of CDP on an interface."
    INDEX      { rcLldpPortCdpConfigIfIndex }
    ::= { rcLldpPortCdpConfigTable 1 }

RcLldpPortCdpConfigEntry ::= SEQUENCE {
    rcLldpPortCdpConfigIfIndex      InterfaceIndex, 
    rcLldpPortCdpConfigAdminState   TruthValue
}

rcLldpPortCdpConfigIfIndex OBJECT-TYPE
    SYNTAX     InterfaceIndex
    MAX-ACCESS not-accessible
    STATUS     current
    DESCRIPTION
            "The ifIndex value of the local interface.
	     It is local port interface index"
    ::= { rcLldpPortCdpConfigEntry 1 }

rcLldpPortCdpConfigAdminState OBJECT-TYPE
    SYNTAX     TruthValue
    MAX-ACCESS read-write
    STATUS     current
    DESCRIPTION
            "Admininstrattely state of the CDP message on the interface.
	    the value of this object has no meaning if CDP compatible mode
	    is globally disabled
	    (rcLldpGlobalCdpCompatibleModeEnbale is set to false)"
    ::= { rcLldpPortCdpConfigEntry 2 }

--
-- The LLDP CDP REMOTE Info Table
--

rcLldpPortCdpRemTable OBJECT-TYPE
    SYNTAX     SEQUENCE OF RcLldpPortCdpRemEntry
    MAX-ACCESS not-accessible
    STATUS     current
    DESCRIPTION
            "The table contains the Remote device information
	     obtained via receiving CDP messages on
	     the local interface. Each rows is per physical network
             connection known to this agent "
    ::= { rcLldpPort 2 }

rcLldpPortCdpRemEntry OBJECT-TYPE
    SYNTAX     RcLldpPortCdpRemEntry
    MAX-ACCESS not-accessible
    STATUS     current
    DESCRIPTION
            
            "An entry of the rcLldpPortCdpRemTable,
            contains the information received via CDP on one
            interface from one device.  Entries is craeted when
	    CDP message is received from neighbor and it is 
	    deleted when CDP is disbaled on interface or globally"
    INDEX      { rcLldpPortCdpRemLocalPortNum, rcLldpPortCdpRemIndex }
    ::= { rcLldpPortCdpRemTable 1 }

RcLldpPortCdpRemEntry ::= SEQUENCE {
    rcLldpPortCdpRemLocalPortNum               InterfaceIndex,
    rcLldpPortCdpRemIndex                      Integer32,
    rcLldpPortCdpRemAddressType                AddressFamilyNumbers,
    rcLldpPortCdpRemAddress                    LldpManAddress,
    rcLldpPortCdpRemVersion                    DisplayString,
    rcLldpPortCdpRemDeviceIdType               INTEGER, 
    rcLldpPortCdpRemDeviceId                   DisplayString,
    rcLldpPortCdpRemPortId                     DisplayString,
    rcLldpPortCdpRemPlatform                   DisplayString,
    rcLldpPortCdpRemCapabilities               LldpSystemCapabilitiesMap,  
    rcLldpPortCdpRemSysName                    DisplayString,
    rcLldpPortCdpRemLastChange                 TimeStamp
}

rcLldpPortCdpRemLocalPortNum  OBJECT-TYPE
     SYNTAX      InterfaceIndex
     MAX-ACCESS  not-accessible
     STATUS      current
     DESCRIPTION
             "The port interface index value used to identify the port component
             (contained in the local chassis with the LLDP/CDP agent)
             associated with this entry.  The rcLldpPortCdpRemLocalPortNum
             identifies the port on which the remote system information
             is received."
     ::= { rcLldpPortCdpRemEntry 1 }

rcLldpPortCdpRemIndex OBJECT-TYPE
    SYNTAX     Integer32 (1..2147483647)
    MAX-ACCESS not-accessible
    STATUS     current
    DESCRIPTION
             "This object represents an arbitrary local integer value used
             by this agent to identify a particular connection instance,
             unique only for the indicated remote system.

             An agent is encouraged to assign monotonically increasing
             index values to new entries, starting with one, after each
             reboot.  It is considered unlikely that the
	     rcLldpPortCdpRemDeviceIndex will wrap between reboots."
    ::= { rcLldpPortCdpRemEntry 2 }

rcLldpPortCdpRemAddressType OBJECT-TYPE
    SYNTAX     AddressFamilyNumbers 
    MAX-ACCESS read-only
    STATUS     current
    DESCRIPTION
            "The type of address identifier encoding used in
             the associated 'rcLldpPortCdpRemAddress' object."
    ::= { rcLldpPortCdpRemEntry 3 }

rcLldpPortCdpRemAddress OBJECT-TYPE
    SYNTAX     LldpManAddress    
    MAX-ACCESS read-only
    STATUS     current
    DESCRIPTION
          "The string value used to identify the management address
          component associated with the remote system.  It is reported
	  in the Address TLV of the most recently received CDP message.
	  And it is associated with rcLldpPortCdpRemAddressType"
    ::= { rcLldpPortCdpRemEntry 4 }

rcLldpPortCdpRemVersion OBJECT-TYPE
    SYNTAX     DisplayString
    MAX-ACCESS read-only
    STATUS     current
    DESCRIPTION
            "The Version string as reported in CDP message"
    ::= { rcLldpPortCdpRemEntry 5 }
    
rcLldpPortCdpRemDeviceIdType OBJECT-TYPE
    SYNTAX     INTEGER { 
                 serialNumber(1), 
                 macAddress(2),
                 other(3) 
               } 
    MAX-ACCESS read-only
    STATUS     current
    DESCRIPTION
             " An indication of the format of Device Id (rcLldpPortCdpRemDeviceId)
	     of remote device."
    ::= { rcLldpPortCdpRemEntry 6 }

rcLldpPortCdpRemDeviceId OBJECT-TYPE
    SYNTAX     DisplayString
    MAX-ACCESS read-only
    STATUS     current
    DESCRIPTION
            "The value of string of remote device as reported in CDP message.
	    The zero-length string indicates no Device-ID field TLV reported"
    ::= { rcLldpPortCdpRemEntry 7 }

rcLldpPortCdpRemPortId OBJECT-TYPE
    SYNTAX     DisplayString
    MAX-ACCESS read-only
    STATUS     current
    DESCRIPTION
    	   "The string value used to identify the port component
    	    associated with the remote system.
            This will typically be the value of the ifName"
    ::= { rcLldpPortCdpRemEntry 8 }

rcLldpPortCdpRemPlatform OBJECT-TYPE
      SYNTAX     DisplayString
      MAX-ACCESS read-only
      STATUS     current
      DESCRIPTION
              "The Device's Hardware Platform as reported in the most
              recent CDP message.  The zero-length string indicates
              that no Platform field (TLV) was reported in the most
              recent CDP message."
      ::= { rcLldpPortCdpRemEntry 9 }

rcLldpPortCdpRemCapabilities OBJECT-TYPE
    SYNTAX     LldpSystemCapabilitiesMap
    MAX-ACCESS read-only
    STATUS     current
    DESCRIPTION
             "The bitmap value used to identify which system capabilities
             are supported on the retome system."
    ::= { rcLldpPortCdpRemEntry 10 }

rcLldpPortCdpRemSysName OBJECT-TYPE	
    SYNTAX     DisplayString (SIZE (0..255))
    MAX-ACCESS read-only
    STATUS     current
    DESCRIPTION
             "The string value used to identify the system name of the
             remote system. The valud of sysName MIB objec "
    ::= { rcLldpPortCdpRemEntry 11 }

rcLldpPortCdpRemLastChange OBJECT-TYPE	
    SYNTAX     TimeStamp
    MAX-ACCESS read-only
    STATUS     current
    DESCRIPTION
        "Indicates the time when this cache entry was last changed.
        This object is initialised to the current time when the entry
        gets created and updated to the current time whenever the value
        of any (other) object instance in the corresponding row is
        modified."
    ::= { rcLldpPortCdpRemEntry 12}

--  extended LLDP remote Table
rcLldpRemExtendedTable OBJECT-TYPE
     SYNTAX      SEQUENCE OF RcLldpRemExtendedEntry
     MAX-ACCESS  not-accessible
     STATUS      current
     DESCRIPTION   "This table is a extended table of lldpRemTable.
                    It contains additional objects for lldpRemTable"
     ::= { rcLldpPort 3 }
     
rcLldpRemExtendedEntry OBJECT-TYPE 
                    
     SYNTAX      RcLldpRemExtendedEntry
     MAX-ACCESS  not-accessible
     STATUS      current
     DESCRIPTION
             "Information about a particular physical network connection.
	      This entry is additinal objects of the lldpRemTable"
     AUGMENTS {	      
     	 lldpRemEntry
     }
     ::= { rcLldpRemExtendedTable 1 }
     
RcLldpRemExtendedEntry ::= SEQUENCE {
       rcLldpRemExtendedProtocolType   INTEGER,
       rcLldpRemExtendedIpAddress      IpAddress
       }
rcLldpRemExtendedProtocolType  OBJECT-TYPE       
   SYNTAX        INTEGER {
                      lldp(1),
		      cdp(2)
                 }
     MAX-ACCESS  read-only
     STATUS      current
     DESCRIPTION   "Indicates the entry is CDP or LLDP protocol"
     ::= { rcLldpRemExtendedEntry 1 }

rcLldpRemExtendedIpAddress   OBJECT-TYPE
      SYNTAX        IpAddress
      MAX-ACCESS    read-only	
      STATUS        current
      DESCRIPTION   "The neighbor Ip address"
      ::= { rcLldpRemExtendedEntry 2}     

 
 
-- Start of ASG

rcASGGlobal OBJECT IDENTIFIER ::= { rcASG 1 }
 
rcASGGlobalEnableStatus  OBJECT-TYPE
        SYNTAX       TruthValue
        MAX-ACCESS   read-only
        STATUS       current
        DESCRIPTION  "Display ASG enable/disable status"
        ::= { rcASGGlobal 1 }
 
rcASGGlobalAccountsTable OBJECT-TYPE
        SYNTAX       SEQUENCE OF RcASGGlobalAccountsEntry
        MAX-ACCESS   not-accessible
        STATUS       current
        DESCRIPTION  "Display ASG supported service login usernames 
                      and their permission levels"
        ::= { rcASGGlobal 2 }
 
rcASGGlobalAccountsEntry OBJECT-TYPE
        SYNTAX       RcASGGlobalAccountsEntry
        MAX-ACCESS   not-accessible
        STATUS       current
        DESCRIPTION  "Contains an entry of rcASGGlobalAccountsEntry 
                      which has username and persmission levels"
        INDEX        { rcASGGlobalAccountsUsername }
        ::= { rcASGGlobalAccountsTable 1 }
 
RcASGGlobalAccountsEntry ::= SEQUENCE {
            rcASGGlobalAccountsUsername      DisplayString,
            rcASGGlobalAccountsAccessLevel   INTEGER
        }
 
rcASGGlobalAccountsUsername OBJECT-TYPE
        SYNTAX       DisplayString
        MAX-ACCESS   not-accessible
        STATUS       current
        DESCRIPTION  "ASG supported username"
        ::= { rcASGGlobalAccountsEntry 1 }
 
rcASGGlobalAccountsAccessLevel   OBJECT-TYPE
        SYNTAX       INTEGER {
                             rwa(1),
                             rw(2),
                             l1 (3),
                             l2 (4)
                           }
        MAX-ACCESS   read-only
        STATUS       current
        DESCRIPTION  "permission level of the username which is mapped 
                      to the existing ACLI user access level"
        ::= { rcASGGlobalAccountsEntry 2 }
 
rcASGGlobalAFHeader OBJECT IDENTIFIER ::= { rcASG 2 }
 
rcASGGlobalAFHeaderAFID OBJECT-TYPE
        SYNTAX       DisplayString (SIZE(0..32))
        MAX-ACCESS   read-only
        STATUS       current
        DESCRIPTION  "Display lacfile/AF AF_ID"
        ::= { rcASGGlobalAFHeader 1 }
 
rcASGGlobalAFHeaderProduct OBJECT-TYPE
        SYNTAX       OCTET STRING (SIZE(0..256))
        MAX-ACCESS   read-only
        STATUS       current
        DESCRIPTION  "Display lacfile/AF product name"
        ::= { rcASGGlobalAFHeader 2 }
 
rcASGGlobalAFHeaderDateAndTime OBJECT-TYPE
        SYNTAX       DateAndTime
        MAX-ACCESS   read-only
        STATUS       current
        DESCRIPTION  "Display lacfile/AF generated date and time"
        ::= { rcASGGlobalAFHeader 3 }
 
rcASGGlobalAFHeaderRelease OBJECT-TYPE
        SYNTAX       DisplayString (SIZE(0..32))
        MAX-ACCESS   read-only
        STATUS       current
        DESCRIPTION  "Display lacfile/AF release version"
        ::= { rcASGGlobalAFHeader 4 }

-- End of ASG

END
