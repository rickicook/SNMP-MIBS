RC-2K-MIB DEFINITIONS ::= BEGIN

IMPORTS
    MODULE-IDENTITY, OBJECT-TYPE, Gauge32, Integer32, IpAddress, Counter64, Unsigned32
        FROM SNMPv2-SMI
    RowStatus, TruthValue, MacAddress, DisplayString
        FROM SNMPv2-TC
    InterfaceIndex
        FROM IF-MIB
    Ipv6Address
        FROM IPV6-TC
    rc2k
        FROM RAPID-CITY;

rc2kMib MODULE-IDENTITY
       LAST-UPDATED "201808100000Z"
       ORGANIZATION 	"Bay Networks, Rapid-City Group"
       CONTACT-INFO 	"Yu-Ten Lee
                	 Postal: 	Nortel Networks, Inc. 
                       	4655 Great America Parkway 
                       	Santa Clara, CA 95052-8185 

                   	 Tel: 	408-495-2560
                   	 Fax: 	408-495-6680
                	 E-mail:	ylee@nortelnetworks.com"

       DESCRIPTION 	"Enterprise MIB for the rc2k."

       REVISION "201808100000Z" -- 10 August 2018
       DESCRIPTION "Version 125: Changed the ES5100 to VSP4600 card type"

       REVISION "201807120000Z" -- 12 July 2018
       DESCRIPTION "Version 124: Added missing comma in rc2kCardFrontType to fix compile error
                                 (azmeu)"
       REVISION "201807120000Z" -- 12 July 2018
       DESCRIPTION "Version 123:  Changed ES6100 Card type to VSP7400"	 

       REVISION "201805310000Z" -- 31 May 2018
       DESCRIPTION "Version 122:  Added MAX-ACCESS	read-write 
				 to rc2kBootConfigHostTftpRetransmit (dcflorea - fix compile err)"

       REVISION "201805220000Z" -- 22 May 2018
       DESCRIPTION "Version 121:  Added ES5100 and ES6100 Card type"	   

       REVISION "201803200000Z" -- 30 Mar. 2018
       DESCRIPTION "Version 120: Remove rc2kBootConfigEnableAppTelemetry
	   			 because it is not needed anymore. (Prem)"
	   
       REVISION "201803280000Z" -- 28 Mar. 2018
       DESCRIPTION "Version 129: Rename rc2kBootConfigEnableApplicationTelemetry to
	   			 rc2kBootConfigEnableAppTelemetry.
	   			 For Application Telemetry feature in VOSS 7.1 (Prem)"
	   
       REVISION "201803270000Z" -- 27 Mar. 2018
       DESCRIPTION "Version 128: Add rc2kBootConfigEnableApplicationTelemetry.
	   			 For Application Telemetry feature in VOSS 7.1 (Prem)"
	   
       REVISION "201802020000Z" -- 02 Feb. 2018
       DESCRIPTION "Version 127: change disable to false for
	                         object rc2kBootConfigEnableFactoryDefaultsMode"	   
       REVISION "201801300000Z" -- 30 Jan. 2018
       DESCRIPTION "Version 126: rc2kBootConfigEnableFactoryDefaultsMode"

       REVISION "201711010000Z" -- 1 Nov. 2017
       DESCRIPTION "Version 125: Added rc2kBootConfigEnableSyslogRfc5424Format"
	   
       REVISION "201709130000Z" -- 13 September 2017
       DESCRIPTION "Version 124: Added rc2kBootConfigHostTable
	                         Requested by Shwetha MS (VSP9K) (ppalarapu)"

       REVISION "201709060000Z" -- 06 September 2017
       DESCRIPTION "Version 123: Added Blinking Amber, Blinking Blue, Solid Blue,
	   			 Blinking Amber Green, Solid Amber Green,
				 Blinking Amber Blue and Solid Amber Blue for
				 the second 4 bits under rc2kChassisPortLed2Status
	                         Requested by Amogha K.G (submit 36024)(ppalarapu)"

       REVISION "201705030000Z" -- 03 May 2017
       DESCRIPTION "Version 122: Added rc2kBootConfigEnableIpv6EgressFilterMode
	   			 in Rc2kBootConfigEntry which was missing.
	                         (prempa)"
       
       REVISION "201704180000Z" -- 18 April 2017
       DESCRIPTION "Version 121: Added rc2kBootConfigEnableIpv6EgressFilterMode.
	                         Requested by A, Karthikeyan (shchang)"

       REVISION "201703290000Z" -- 29 March 2017
       DESCRIPTION "Version 120: Removed rc2kBootConfigMasterCPUSlot,
	   			 rc2kBootConfigEnableHaCpu and 
                                 rc2kBootConfigEnableSavetoStandby because
				 we don't need them and they were never part
				 of any release. So removing them from MRT as
				 well. Also, adjusted the OID for rc2kBootConfigVcMode.
	   			 (prempa)."
       
       REVISION "201703170000Z" -- 13 March 2017
       DESCRIPTION "Version 119: added rc2kBootConfigVcMode.
	   			 Requested by Zuyan Wang (zuyanwa)."
       REVISION "201702170000Z" -- 17 February 2017
       DESCRIPTION "Version 118: Added the values - upMaster, upDormant and upWarmStandby
	   			 to rc2kCardFrontOperStatus to accomodate the additional 
				 oper status values for slots 1 and 2 on VSP8600.
	   			 Requested by Eeranna Sajjanar (prempa)"

       REVISION "201612050000Z" -- 05 December 2016
       DESCRIPTION "Version 117: Increased the size of rc2kChassisPortLed2Status
	   			 from 512 to 1024 to accomodate ports on VSP8600.
	   			 Requested by Joy Jis (prempa)"

       REVISION "201612050000Z" -- 05 December 2016
       DESCRIPTION "Version 116: added rc2kBootConfigMasterCPUSlot, 
                                 rc2kBootConfigEnableHaCpu and 
                                 rc2kBootConfigEnableSavetoStandby.
	   			 Requested by Mircea Lovin (zuyanwa)"

       REVISION "201609080000Z" -- 8 September 2016
       DESCRIPTION "Version 115: Under rc2kCardFrontType - renamed vsp9k9424XS, 
	   			 vsp9k9424XT, vsp9k9416QQ, vsp9k9406CQ and 
				 vspSF9400 to vsp8624XS, vsp8624XT, vsp8616QQ, 
				 vsp8606CQ and vsp8600SF. Added vsp8608.
	   			 (prempa)"

       REVISION "201606300000Z" -- 30 June 2016
       DESCRIPTION "Version 114: added rc2kBootConfigLinerateDirectedBroadcast.
	   			 Requested by Steve DiCecco (prempa)"

       REVISION "201605200000Z" -- 20 May 2016
       DESCRIPTION "Version 113: added rc2kChassisPortLed3Status"
	   	   
       REVISION "201605020000Z" -- 02 May 2016
       DESCRIPTION "Version 112: added rc2kBootConfigEnableVrfScaling"
	   
       REVISION "201604260000Z" -- 26 April 2016
       DESCRIPTION "Version 111:  Changed the name of 
	   		 rc2kBootConfigEnableVxlanGwInterworkingMode to
			 rc2kBootConfigEnableVxlanGwFullInterworkingMode.
			 Requested by Amruta Manjunath Bhat (prempa)"

       REVISION "201603310000Z" -- 31 Mar 2016
       DESCRIPTION "Version 110:  Added rc2kBootConfigEnableDvrLeafMode"
	   
       REVISION "201603230000Z" -- 23 Mar 2016
       DESCRIPTION "Version 109: correct the vsp8k8402CQ definition"
	   
       REVISION "201603020000Z" -- 02 Mar 2016
       DESCRIPTION "Version 108: Changed/corrected the object name from
	                         rc2kBootConfigEnableSpbmBandwidthReservation to
	                         rc2kBootConfigAdvancedFeatureBwReservation
				 Added the DSG family cards"
	   
       REVISION "201601190000Z" -- 19 Jan. 2016
       DESCRIPTION "Version 107: Changed the syntax of 
	   			 rc2kBootConfigEnableEnhancedsecureMode
	   			 from TruthValue to INTEGER {
				 	jitc(1), 
					disable(2),
					non-jitc(3)
                                 }
	   			 Requested by Prasad Saran/Hari for 
				 Federal certification (prempa)."
	   
       REVISION "201601120000Z" -- 12 Jan. 2016
       DESCRIPTION "Version 106: added rc2kBootConfigNniMstp.
	   			 Requested by Zuyan Wang (prempa)."
	   
       REVISION "201511280000Z" -- 28 Nov. 2015
       DESCRIPTION "Version 105:   added rckBootConfigEnableVxlanGwInterworkingMode "
	   	   
       REVISION "201511100000Z" -- 10 Nov. 2015
       DESCRIPTION "Version 104:   Update rc2kChassisPortLed2Status"
	   
       REVISION "201511090000Z" -- 09 Nov. 2015
       DESCRIPTION "Version 103: Added rc2kBootConfigEnableSpbmBandwidthReservation.
	   			 Requested by Shuching Shieh (submit 23528) (prempa)"
	   
       REVISION "201511050000Z" -- 05 Nov. 2015
       DESCRIPTION "Version 102: Added rc2kBootConfigEnableFlowControlMode"
	   
       REVISION "201510230000Z" -- 23 October 2015
       DESCRIPTION "Version 101: Added rc2kChassisPortLicenseStatus"
	   
       REVISION "201510010000Z" -- 01 October 2015
       DESCRIPTION "Version 100: Added comments under second 4 bits value - 
	   			 meaning for Speed for rc2kChassisPortLed2Status"

       REVISION "201509220000Z" -- 22 September 2015
       DESCRIPTION "Version 99:	 Added vspSF9400(1411293440) to rc2kCardFrontType"

       REVISION "201505140000Z" -- 14 May 2015
       DESCRIPTION "Version 98:	 Added rc2kBootConfigUrpfModeEnable"
	   
       REVISION "201504170000Z" -- 17 April 2015
       DESCRIPTION "Version 97: Corrected CardType definition
	                           netApp8016QQ(895778868)
	                           vsp9k9424XS(1446215960)
				   vsp9k9424XT(1445167384)
				   vsp9k9416QQ(1446281500)
				   vsp9k9406CQ(1446347032)"
				  
       REVISION "201504100000Z" -- 16 April 2015
       DESCRIPTION "Version 96: Added netAppL8016QQ(895778868)
	   			      vsp9k9424XS(1379107096),
	                              vsp9k9424XT(1378058520),
				      vsp9k9416QQ(1379172636),
				      vsp9k9406CQ(1379238168)"
	   
       REVISION "201504100000Z" -- 10 April 2015
       DESCRIPTION "Version 95: Added vsp8k8402CQ"

       REVISION "201502250000Z" -- 25 Feb 2015
       DESCRIPTION "Version 94: Modified rc2kDeviceUsbFileSlot's range."
	   
       REVISION "201411050000Z" -- 05 Nov 2014
       DESCRIPTION "Version 93: added vsp4k4450GSX"
			    	   
       REVISION "201411050000Z" -- 05 Nov 2014
       DESCRIPTION "Version 92: removed vsp7k7254XSQ and vsp7k7254XTQ.
	                        Added vsp7k7248XS, vsp7k7206QQ and vsp7k7248XT"
			    
       REVISION "201411040000Z" -- 04 Nov 2014
       DESCRIPTION "Version 91: Changes made in version 90 was by mistake. So removing them - Prem"
	   
       REVISION "201411040000Z" -- 04 Nov 2014
       DESCRIPTION "Version 90: Removed the extra lines at the back 
	   			end of this file"
	   
       REVISION "201410150000Z" -- 15 Oct 2014
       DESCRIPTION "Version 89: added vsp7k7254XSQ to vsp7k7254XTQ"
	   	   	   
       REVISION "201410090000Z" -- 09 Oct 2014
       DESCRIPTION "Version 88: Changed rc2kBootConfigEnableFederalMode to
	                        rc2kBootConfigEnableEnhancedsecureMode"
	   	   
       REVISION "201409230000Z" -- 23 Sept 2014
       DESCRIPTION "Version 87: added rc2kChassisPortLed2Status "

       REVISION "201409170000Z" -- 17 Sept 2014
       DESCRIPTION "Version 86: Changed rc2kBootConfigIpv6ModeEnable to
	                        rc2kBootConfigEnableIpv6Mode.
				rc2kBootConfigFederalMode to
				rc2kBootConfigEnableFederalMode"
	   
       REVISION "201409140000Z" -- 14 Sept 2014
       DESCRIPTION "Version 85: Added rc2kBootConfigFederalMode"	   

       REVISION "201409090000Z" -- 09 Sept 2014
       DESCRIPTION "Version 84: Added 
	   			vsp8k8404(1331823105),
				vsp8k8424XS(1298379288),
				vsp8k8424XT(1293136408),
				vsp8k8408QQ(1298432544),
				vsp8k8418XSQ(1298461208),
				vsp8k8418XTQ(1299509784),
				vsp8k8424GS(1298326040),
				vsp8k8424GT(1294107160)"
			    
       REVISION "201406120000Z" -- 12 June 2014
       DESCRIPTION "Version 83:	Update description for
	                        rc2kBootConfigEnableSpbmConfigMode"
	   	   
       REVISION "201406040000Z" -- 04 June 2014
       DESCRIPTION "Version 82:	Added rc2kBootConfigIpv6ModeEnable"
	   
       REVISION "201406030000Z" -- 03 June 2014
       DESCRIPTION "Version 81:  Changed the description of the following
                                 mib objects to indicate a value of 0 would
				 mean that the sensor is not available -
				 rc2kIoCardTemperatureFPGASensor1Temperature,
				 rc2kIoCardTemperatureFPGASensor2Temperature,
				 rc2kIoCardTemperatureFPGASensor3Temperature,
				 rc2kIoCardTemperatureFPGASensor4Temperature,
				 rc2kIoCardTemperatureFPGASensor5Temperature,
				 rc2kIoCardTemperatureFPGASensor6Temperature,
				 rc2kIoCardTemperatureFPGASensor7Temperature,
				 rc2kIoCardTemperatureFPGASensor8Temperature,
				 rc2kIoCardTemperatureFPGASensor9Temperature,
				 rc2kIoCardTemperatureFASensor1Temperature,
				 rc2kIoCardTemperatureFASensor2Temperature and
				 rc2kIoCardTemperatureFASensor3Temperature"

       REVISION "201405140000Z" -- 14 May 2014
       DESCRIPTION "Version 80:  added vsp4k4450GTXHTPWRPLUS
	                         changed a4950GSXPWRPLUS(1231228978) to
				 a4450GSXPWRPLUS(1231228978)"
	   	   
       REVISION "201405130000Z" -- 13 May 2014
       DESCRIPTION "Version 79:  added rc2kBootConfigEnableSpbmConfigMode"
	   
       REVISION "201402140000Z" -- 14 Feb. 2014
       DESCRIPTION "Version 78:  Corrected the synatx"
	   
       REVISION "201401270000Z" -- 27 Jan. 2014
       DESCRIPTION "Version 77:  Added rc2kCardAsicInfoTable and 
	   			 rc2kIoCardTemperatureTable"

       REVISION "201401100000Z" -- 10 Jan. 2014
       DESCRIPTION "Version 76:  Added vsp8k8242XSQ card type"
	   
       REVISION "201311150000Z" -- 15 November 2013
       DESCRIPTION "Version 75:  Added cbHSFanTray and correct the value
	                         for cbFanTray for rc2kCardFrontType."
	   
       REVISION "201311130000Z" -- 13 November 2013
       DESCRIPTION "Version 74: Added vsp4k4950GSXPWRPLUS, added
				comment - For Line card or MDA
				0 = 1 prototype 1 = product under
			        field e for rc2kCardFrontType."

       REVISION "201308090000Z" -- 09 Aug 2013
       DESCRIPTION "Version 73: Correct card type field definition "
	   
       REVISION "201307300000Z" -- 30 July 2013
       DESCRIPTION "Version 72: Added 'c' field defintion for VSP4K device "
	   	   
       REVISION "201307100000Z" -- 10 July 2013
       DESCRIPTION "Version 71: Modified the values for rof4x40GBaseSFP and rof12x40GBaseSFP and
	   			also modified the Maximum Speed bit field description for 40Gbit 
				and 100Gbit for VSP."
	   
       REVISION "201305070000Z" -- 07 May. 2013
       DESCRIPTION "Version 70: Added rc2kBootConfigLinecardCompatibilityMode"
	   
       REVISION "201212250000Z" -- 25 Dec. 2012
       DESCRIPTION "Version 69: Added rc2kDeviceGlobalIntflashBytesUsed and
	                              rc2kDeviceGlobalIntflashBytesFree"

       REVISION "201212110000Z" -- 11 Dec. 2012
       DESCRIPTION "Version 68: Added rc2kChassisPortLedStatus"
	   
       REVISION "201212110000Z" -- 11 Dec. 2012
       DESCRIPTION "Version 67: Added rc2kUsbTable"


       REVISION "201210220000Z" -- 22 Oct. 2012
       DESCRIPTION "Version 66: Added cbACPowerPlusSupply and cbFanTray 
	   			under rc2kCardFrontType"

       REVISION "201210080000Z" -- 08 Oct. 2012
       DESCRIPTION "Version 65: Added cbMidplaneSapphire and cbSF9610
	   			under rc2kCardFrontType"

       REVISION "201209180000Z" -- 18 Sept. 2012
       DESCRIPTION "Version 64: correct card type
	   			vsp4k4850GTSPWRPLUS(1232277554)"
	   
       REVISION "201208160000Z" -- 16 Aug. 2012
       DESCRIPTION "Version 63: Added, 	vsp4k4850GTS(1232273458),
	                                vsp4k4850GTSPWR(1232277554)"
	   
       REVISION "201207310000Z" -- 31 July 2012
       DESCRIPTION "Version 62: added   rof48x1000SFP(1144152880),
	   				rofLoadBoard(1144152832),
					rof16x10GBaseSFP(1144218384),
					rof48x10GBaseSFP(1144218416),
					rof4x40GBaseSFP(1144283908),
					rof12x40GBaseSFP(1144283916)"
				    
       REVISION "201204250000Z" -- 25 April 2012
       DESCRIPTION "Version 61: rc2kPRE12X10GBaseXLJ(632512780)"
	   	   
       REVISION "201203070000Z" -- 07 March 2012
       DESCRIPTION "Version 60: Modified rc2kPR12X10GBaseJXLRS to
	   	    rc2kPR12X10GBaseXLRSJ under rc2kCardFrontType."
	   
       REVISION "201202270000Z" -- 27 February 2012
       DESCRIPTION "Version 59: Added rc2kPR12X10GBaseJXLRS(607346956) under
	            rc2kCardFrontType. Also added the '110 = 10GE LAN serial 
		    1310nm (JXLR)' under the description for rc2kCardFrontType
		    for Card Specific Info (field f)"
	   
       REVISION "201201230000Z" -- 23 Jan 2012
       DESCRIPTION "Version 58: Added pcmciaStart option" 

       REVISION "201111290000Z" -- 29 November 2011
       DESCRIPTION "Version 57: Changed the names of 
	            rc2kTemperatureInlet1Temperature,
	            rc2kTemperatureInlet2Temperature,
		    rc2kTemperatureInlet3Temperature,
		    rc2kTemperatureOutlet1Temperature and
		    rc2kTemperatureOutlet2Temperature to 
		    rc2kTemperatureZone1Temperature, 
		    rc2kTemperatureZone2Temperature,
		    rc2kTemperatureZone3Temperature,
		    rc2kTemperatureZone4Temperature and
		    rc2kTemperatureZone5Temperature."

       REVISION "201111110000Z" -- 11 November 2011
       DESCRIPTION "Version 56: Added rc2kTemperatureInlet1Temperature,
	            rc2kTemperatureInlet2Temperature,
		    rc2kTemperatureInlet3Temperature,
		    rc2kTemperatureOutlet1Temperature and
		    rc2kTemperatureOutlet2Temperature to rc2kTemperatureTable.
		    Modified the OID for rc2kTemperatureHighTemperature,
		    rc2kTemperatureLowTemperature,
		    rc2kTemperatureAlarmThreshold and 
		    rc2kTemperatureShutdownThreshold"

       REVISION "201109120000Z" -- 12 September 2011
       DESCRIPTION "Version 55: Added rc2kTemperatureTable"

       REVISION "201107270000Z" -- 27 July 2011
       DESCRIPTION "Version 54: Added rc2kBootConfigEnableCfPcCompat"

       REVISION "201102040000Z" -- 04 Feb 2011
       DESCRIPTION "Version 53: correct the object name
	                        for rc2kCardModSerialNum,
	                        rc2kCardModPartNumber,
	                        rc2kCardModAssemblyDate
				as rc2kCardModuleSerialNum,
	                        rc2kCardModulePartNumber,
	                        rc2kCardModuleAssemblyDate"
       REVISION "201101190000Z" -- 19 January 2011
       DESCRIPTION "Version 52: Added rc2kCardModSerialNum,
	                        rc2kCardModPartNumber,
	                        rc2kCardModAssemblyDate."
       REVISION "201101060000Z" -- 06 January 2011
       DESCRIPTION "Version 51: Added rc2kPRE48x1000BaseGB(632443184),
	            rc2kPRE48x1000BaseGT(631406896), 
		    rc2kPRE12X10GBaseXL(632504588) and 
		    rc2kPRE34xXG(632443170) enum values to rc2kCardFrontType.
		    Also added rc2kEEDPM2(630128906) and rc2kEEDPM3(630129087)
		    enum values to rc2kCardBackType." 

       REVISION "201009150000Z" -- 15 September 2010
       DESCRIPTION "Version 50: Added the following:
                                   rc2kChassisSystemTempLedColor,
                                   rc2krc2kDeviceGlobalUsbBytesUsed,
                                   rc2kDeviceGlobalUsbBytesFree,
                                   rc2kDeviceGlobalUsbNumFiles,
                                   rc2kDeviceGlobalExtflashBytesUsed,
                                   rc2kDeviceGlobalExtflashBytesFree,
                                   rc2kDeviceGlobalExtflashNumFiles,
                                   rc2kDeviceExtflashFileTable,
                                   rc2kDeviceUsbFileTable,
                                   rc2kCardSlotPower,
                                   rc2kPowerConsumptionInfoTable..
                                Updated range for rc2kBootConfigSlot,
                                                  rc2kCardIndex,
                                Added VSP card types to rc2kCardFrontType" 

       REVISION "201008230000Z" -- 23 August 2010
       DESCRIPTION "Version 49: Updated rc2kCPUTypePrimary and rc2kCPUTypeSecondary 
	            with cpu8895Default enumeration."

       REVISION "200909140000Z" -- 14 September 2009
       DESCRIPTION "Version 48: Updated rc2kCpuEthernetPortOperSpeed."

       REVISION "200904200000Z" -- 20 April 2009
       DESCRIPTION "Version 47: Added rc2kSysAggrRateLimiterStatsTable  as rc2k 16."

       REVISION "200903110000Z" -- 11 March 2009
       DESCRIPTION "Version 46: 
                                      Added rc2kCPURed for rc2kCPURed,
                                      cpu8695Default for rc2kCPUTypePrimary,
                                      cpu8695Default for rc2kCPUTypeSecondary, 
                                      mem1024MB for rc2kCPUTypePrimaryMemory 
                                      mem1024MB for rc2kCPUTypeSecondaryMemory ."

       REVISION "200902190000Z" -- 19 Feb 2009
       DESCRIPTION "Version 45: Added rc2kChassisPbtMacAddrList"

       REVISION "200812110000Z" -- 11 Dec 2008
       DESCRIPTION "Version 44: Added enum value mem512MB(4) to rc2kCPUTypePrimaryMemory
                                and rc2kCPUTypeSecondaryMemory."

       REVISION "200809260000Z" -- 26 Sept 2008
       DESCRIPTION "Version 43:Modified Rc2kBootConfigEntry, rc2kBootConfigSlot.
                                                        Added rc2kBootConfigEnableAutoAssignIp, rc2kBootConfigUpgradeBootImageSource,
                                                        rc2kBootConfigUpgradeRuntimeImageSource, rc2kBootConfigUpgradeMezzImageSource,
                                                        rc2kBootConfigUpgradeConfigSource, rc2kBootConfigUpgradeRModImageSource,
                                                        rc2kBootConfigUpgradeRCModImageSource, rc2kBootConfigUpgradeESMImageSource,
                                                        rc2kBootConfigFallBackBootImageSource, rc2kCardPerfTable, rc2kCardPerfEntry ,
                                                        Rc2kCardPerfEntry, rc2kCardPerfId, rc2kCardPerfDramSize, rc2kCardPerfDramUsed,
                                                        rc2kCardPerfDramFree, rc2kCardPerfCPUUtilization "

       REVISION "200807210000Z" -- 21 July 2008
       DESCRIPTION "Version 42: Update DESCRIPTION of rc2kCardFrontType item c."
       
       REVISION "200806270000Z" -- 27 June 2008
       DESCRIPTION "Version 41: Update DESCRIPTION of rc2kCardFrontType item f,
                                Add 010 = PoE 1770W AC PSU
                                    011 = PoE 1400W AC PSU."
       
       REVISION "200805290000Z" -- 29 May 2008
       DESCRIPTION "Version 40: Added rc2kPP8300-CPU8x1000BaseSFP256 enum in rc2kCardFrontType table."

       REVISION "200805170000Z" -- 17 May 2008
       DESCRIPTION "Version 39: Added rc2kCardSlotOriginalPriority back as 30 and
				moved rc2kCardMode to 31."

       REVISION "200805160000Z" -- 16 May 2008
       DESCRIPTION "Version 38: Added rc2kEDPM2 and rc2kEDPM3 to rc2kCardBackType."

       REVISION "200803140000Z" -- 14 March 2008
       DESCRIPTION "Version 37: Removed rc2kCardSlotOriginalPriority
 	                        Added rc2kCardMode
				Modified rc2kBootConfigUnknownDstMacDiscard,
			 	         rc2kBootConfigUnknownDstMacDiscardOperStatus,
					 rc2kCardFrontType description"

       REVISION "200801300000Z" -- 30 Jan 2008
       DESCRIPTION "Version 36: Added rc2kCardSlotOriginalPriority, modified
				the description of rc2kCardSlotPriority and 
				modified the syntax of rc2kCardFrontAdminStatus"

       REVISION "200712060000Z" -- 06 Dec 2007
       DESCRIPTION "Version 35: Added rc2kCardModTable,
	                        Modified rc2kCardMezzSerialNum"

       REVISION "200710020000Z" -- 02 Oct 2007
       DESCRIPTION "Version 34: Added a missing comma in rc2kCardFrontType"

       REVISION "200708160000Z" -- 16 Aug 2007
       DESCRIPTION "Version 33: Updated rc2kCardFrontType"

       REVISION "200704220000Z" -- 22 Apr 2007
       DESCRIPTION "Version 32: Added rc2kChassisPbtMacAddr and rc2kChassisUserLabel1"

       REVISION "200704170000Z" -- 17 Apr 2007
       DESCRIPTION "Version 31: Added rc2kCardSlotPriority."

       REVISION "200703260000Z" -- 26 Mar 2007
       DESCRIPTION "Version 30: Added rc2kPP8300-CPU2x10GBaseXFP(1342390530), rc2kPP8300-8x10GBaseXFP-4B(1345519880) to rc2kCardFrontType"

       REVISION "200702121000Z" -- 12 Feb 2007
       DESCRIPTION "Version 29: Added rc2kPR48x1000BaseGBRS(607277360), rc2kPR48x1000BaseGTRS(606241072), 
		rc2kPR12X10GBaseXLRS(607338764), rc2kPR34xXGRS(607277346) to rc2kCardFrontType"

       REVISION "200702120000Z" -- 12 Feb 2007
       DESCRIPTION "Version 28: Added Flash1 related mib definition"

       REVISION "200608020000Z" -- 02 Aug 2006
       DESCRIPTION "Version 27: Added objects 30-34 under rc2kBootConfigEntry"

       REVISION "200607200000Z" -- 20 Jul 2006
       DESCRIPTION "Version 26: Added rc2kPP8300-48x1000BaseSFP-2B"

       REVISION "200604270000Z" -- 27 Apr 2006
       DESCRIPTION "Version 25: Added rc2kCardMezzSerialNum , rc2kCardMezzHwVersion, & rc2kCardMezzPartNumber"

       REVISION "200602270000Z" -- 27 Feb 2006
       DESCRIPTION "Version 24: Added ESM card type rc2k8x1000BaseOPM"

       REVISION "200602150000Z" -- 15 Feb 2006
       DESCRIPTION "Version 23: Removed Thunderbolt due to project cancellation"

       REVISION "200512210000Z" -- 21 Dec 2005
       DESCRIPTION "Version 22: Changed the INTEGER value for rc2kCPUTypeGeneralGroup"

       REVISION "200510200000Z" -- 20 Oct 2005
       DESCRIPTION "Version 21: Changed the range of rc2kDeviceGlobalSlot, rc2kDeviceFlashFileSlot & rc2kBootConfigSlot"
       REVISION "200510170000Z" -- 17 Oct 2005
       DESCRIPTION "Version 20: Added card types rc2kPP8300-48x1000BaseTX-4B & rc2kPP8300-48x1000BaseTXPOE-4B for Rainier"

       REVISION "200510121800Z" -- 12 Oct 2005
       DESCRIPTION "Version 19: Updated the range from 0..64 to 0..255 for 		                          		rc2kBootConfigPrimaryBackupConfigSource,
		rc2kBootConfigSecondaryBackupConfigSource,
		rc2kBootConfigTertiaryBackupConfigSource,
		rc2kBootConfigMezzImageSource"
       REVISION "200510120000Z" -- 12 Oct 2005
       DESCRIPTION "Version 18: Updated the range from 0..64 to 0..255 for 		                                                                  rc2kBootConfigLastBootConfigSource,
                                        rc2kBootConfigLastRuntimeImageSource, 		                                                                                       rc2kBootConfigLastRuntimeConfigSource, 		                                                                                       rc2kBootConfigPrimaryImageSource, 
	                   rc2kBootConfigPrimaryConfigSource, 				                                            rc2kBootConfigSecondaryImageSource, 				                                            rc2kBootConfigSecondaryConfigSource, 				                                            rc2kBootConfigTertiaryImageSource, 
	                   rc2kBootConfigTertiaryConfigSource"
       REVISION "200509140000Z" -- 14 Sep 2005
       DESCRIPTION "Version 17: Updated rc2kPR48X1000BaseTX"
       REVISION "200509090000Z" -- 09 Sep 2005
       DESCRIPTION "Version 16: Added rc2kCpuEthernetPortIpv6RouteTable"
       REVISION "200508300000Z" -- 30 Aug 2005
       DESCRIPTION "Version 15: Added objects under rc2kCPUTypeGeneralGroup"
       REVISION "200508150000Z" -- 15 Aug 2005
       DESCRIPTION "Version 14: Updating the range for 2k device objects"
       REVISION "200505230000Z" -- 23 May 2005
       DESCRIPTION "Version 13: Undoing version #12 in order to be consistent with the code"
       REVISION "200502211200Z" -- 21 February 2005
       DESCRIPTION "Version 12: Now using rc2kPP8300-48x100BaseTXPOL instead of POE"  
       REVISION "200412100000Z" -- 12 December 2004
       DESCRIPTION "Version 11: Added rc2kBootConfigEnableMezz."  
       REVISION "200410280000Z" -- 28 October 2004
       DESCRIPTION "Version 10: Replaced rc2kPR3X10GBaseGbic(607346947) with
                                rc2kPR3X10GBaseGbic(607338755) and added
                                rc2kPR3X10GBaseXZW(607346947) in rc2kCardFrontType."
       REVISION "200408250001Z" -- 25 August 2004
       DESCRIPTION "Version 7: Added rc2kBootConfigMezzImageSource."
       REVISION "200408250000Z" -- 25 August 2004
       DESCRIPTION "Version 6: Added rc2kPP8300-24X100BaseFX(1345388824) in
                               rc2kCardFrontType.
                               Fix typos for rc2kPP8300-48x1000BaseTXPOE" 
       REVISION "200408090000Z" -- 09 August 2004
       DESCRIPTION "Version 6: Added rc2kPR48X1000BaseT(606208304) in
                               rc2kCardFrontType.
                               Added rc2kDPM2(613351682) in rc2kCardBackType" 

       REVISION "200407200000Z" -- 20 July 2004
       DESCRIPTION "Version 5: Added version info"  

       ::= { rc2k 0 }


-- rc2k Group

rc2kChassis     OBJECT IDENTIFIER ::= { rc2k 1 }

rc2kChassisPortOperStatus  OBJECT-TYPE
        SYNTAX          OCTET STRING (SIZE(256))
        MAX-ACCESS      read-only
        STATUS          current
        DESCRIPTION     "A bit array that contains the oper-status
                        of the ports in the device.  2 bits are used
                        for each port.  The high order 2 bits of the
                        first octet represent port #0, the next two
                        bits are used for port #1, etc.  The status
                        is encoded with the following scheme :

                        value   meaning
                        -----   -------
                          0     no-link (admin=up, oper=down)
                          1     up	(admin=up, oper=up)
                          2     down	(admin=down, oper=down)
                          3     testing	(admin=test, oper=test)
                        "
        ::= { rc2kChassis 1 }

rc2kChassisTemperature OBJECT-TYPE
        SYNTAX          Gauge32
        MAX-ACCESS      read-only
        STATUS          current
        DESCRIPTION     "Used to indicate the core operating temperature
                        of the chassis.  This value represents the degree
			in celsius of the air inside the chassis."
        ::= { rc2kChassis 2 }

rc2kChassisAmbientLowerTemperature OBJECT-TYPE
        SYNTAX          Gauge32
        MAX-ACCESS      read-only
        STATUS          obsolete
        DESCRIPTION     "Used to indicate the temperature of the air
                        entering the fan at the lower half of the chassis."
        ::= { rc2kChassis 3 }

rc2kChassisAmbientUpperTemperature OBJECT-TYPE 
        SYNTAX          Gauge32 
        MAX-ACCESS      read-only 
        STATUS          obsolete 
        DESCRIPTION     "Used to indicate the temperature of the air
                        entering the fan at the upper half of the chassis." 
        ::= { rc2kChassis 4 }

rc2kChassisBaseMacAddr OBJECT-TYPE 
        SYNTAX          MacAddress 
        MAX-ACCESS      read-only 
        STATUS          current 
        DESCRIPTION     "base mac addr"
        ::= { rc2kChassis 5 }

rc2kChassisMacAddrCapacity OBJECT-TYPE
        SYNTAX          Integer32
	MAX-ACCESS      read-only
	STATUS          current
	DESCRIPTION     "Mac Address Capacity"
	::= { rc2kChassis 6 }

rc2kChassisPbtMacAddr OBJECT-TYPE 
        SYNTAX          MacAddress 
        MAX-ACCESS      read-only 
        STATUS          current 
        DESCRIPTION     "pbt mac addr"
        ::= { rc2kChassis 7 }

rc2kChassisUserLabel1 OBJECT-TYPE 
        SYNTAX          DisplayString (SIZE(0..89))
        MAX-ACCESS      read-write 
        STATUS          current 
        DESCRIPTION     "user defined management information. This can be used to
                         provide extra information about the chassis. Syntax can be
                         as expected by the management system "
        ::= { rc2kChassis 8 }

rc2kChassisPbtMacAddrList OBJECT-TYPE
	SYNTAX          OCTET STRING (SIZE(0..48))
	MAX-ACCESS	read-only
	STATUS		current
	DESCRIPTION	"List of 8 Pbt Mac addresses. The first Pbt Mac Address
			is rc2kChassisPbtMacAddr. The other 7 Pbt Mac Addresses
			are derived by increment 1 to the previous mac sequencially
			start from rc2kChassisPbtMacAddr"
	::= { rc2kChassis 9}

rc2kChassisSystemTempLedColor OBJECT-TYPE
        SYNTAX          INTEGER {
                           green(1),
                           red(2),
                           amber(3)
                        }
        MAX-ACCESS      read-only
        STATUS          current
        DESCRIPTION     "Used to indicate the led color of the system temperature
                         which is under or above the threshold.  The threshold is 60 degree
                         in celsius.
                         'green' means normal. And temperature under threshold.
                         'red' means one of the zone temperature is above the threshold.
                         'amber' is the initial state, means device have not start to
                               check the temperature yet."

        ::= { rc2kChassis 10 }

rc2kChassisPortLedStatus  OBJECT-TYPE
        SYNTAX          OCTET STRING (SIZE(256))
        MAX-ACCESS      read-only
        STATUS          current
        DESCRIPTION     "This is applicable only for VSP4K. Max port 3/64
	                A bit array that contains the LED status
                        of the ports in the device.  1 octet is used
                        for each port. Starting at postion as ifIndex.
			Such 192 octet for 1/1, 193 for 1/2, so on so forth.
			The high order 5 bit of the octet represent Speed,
			the next 3 bits of activity.  The status is encoded
			with the following
			scheme :

                        bit   meaning for Speed.
                        ----- ------------------
                          0     green   (1000 Mbps)
                          1     amber	(100 Mbps)
                          2     Off     (10 Mbps)
                          3     blinking (PoE+)
			  4     Amber/Green (pulse _AG)  (PoE error) 
			bit  meaning for activity
			---- --------------------
			  5     green  (link Up. No Data activity)
			  6     amber  (port Admin disabled)
			  7     blink  (Green: link up and data acvity)
			               (Amber: Port Not used)
       			  "
        ::= { rc2kChassis 11 }

rc2kChassisPortLed2Status  OBJECT-TYPE
        SYNTAX          OCTET STRING (SIZE(1024))
	MAX-ACCESS      read-only
	STATUS          current
	DESCRIPTION     "This is applicable only for VSP8200, VSP8400 & VSP8600. 
                         Each octet string contains the value of a port LED status. One octet 
			 is used for each port. Each octet contains two nibbles (two 4 bits). 
			 From left to right, the first nibble (higher order 4 bits) of the 
			 octet represents the Link/Activity LED (The left one of the two for 
			 fiber port. Each copper port has only one LED). The second nibble 
			 (lower order 4 bits) of the octet represents the Speed/InUse LED (The 
			 right one of the two for fiber port). And use the ifIndex as the position
			 starting from 192th octet. Such 192th octet for 1/1, 193 for 1/2, so on 
			 so forth.

			 The following shows the meaning for each nibbles:

			 first 4 bits value                       meaning for activity
                         --------------------------------------------------------------------------------------------------------
                             0                                    : port not valid or not present
			     1        Light Off 		  : admin enabled & no link & no fault
			     					    on all channels
			     2        Slow Blinking Green         : admin disable 
			     					    or one or more channelized ports admin disable 
			     3        Blinking Amber 		  : remote fault on 10G/40G fiber port
			     4        Solid Amber                 : local fault on one or more 
			                                            channels on 10G/40G fiber port
			     5        Solid Green                 : link up & no activity on one or more 
			     					    channels on 10G/40G fiber port
								  : link up with 100M speed on 10G copper port 
			     6        Solid Amber                 : link up with 1G speed on 10G copper port
			     7        Solid Blue                  : link up with 10G speed on 10G copper port 
			     8        Random Blinking Green       : link up & activity on one or more 
			     					    channels on 10G/40G fiber port
								  : activity with 100M speed on 10G copper port
			     9        Random Blinking Amber       : activity with 1G speed on 10G copper port
			     10       Random Blinking Blue        : activity with 10G speed on 10G copper port

			 second 4 bits value                      meaning for Speed.
                         ------------------------------------------------------------------------------------------------------
                             0                                    : port not valid or not present
			     1        Blinking Green              : 1G speed on 10G fiber port(SFP+) 
			     2        Solid Green                 : 10G speed on 10G fiber port
			                                          : channelized on on 40G fiber port
							          : 1G speed on 1G port  
			     3        Light Off                   : channelized off on 40G fiber port
				  	     	   	          : 10M speed on 1G port
			     4        Solid Amber                 : 100M speed on 1G port
			     5        Blinking Amber              : Copper port link up with 100Mbps speed with PoE
			     6        Blinking Blue               : Copper port link up with 10Gbps speed with PoE
			     7        Solid    Blue               : Copper port link up with 10Gbps speed
			     8        Blinking Amber Green        : Copper port link up with 2.5Gbps speed with PoE
			     9        Solid Amber Green           : Copper port link up with 2.5Gbps speed
			     10       Blinking Amber Blue         : Copper port link up with 5Gbps speed with PoE
			     11       Solid Amber Blue            : Copper port link up with 5Gbps speed"	  
	::= { rc2kChassis 12 }
    
rc2kChassisPortLicenseStatus  OBJECT-TYPE
        SYNTAX          OCTET STRING (SIZE(56))
        MAX-ACCESS      read-only
        STATUS          current
        DESCRIPTION     "This is applicable only for VSP7K. The string is 56 octets long,
			for a total of 448 bits. Each bit corresponds to a port, as represented
			by its ifIndex value. When a bit is set (value 1), the corresponding
			port is disabled by license and the port is not allowed to be enabled.
			The encoding is such that the most significant bit of octet #1 corresponds
			to ifIndex 0, while the least significant bit of octet #56 corresponds
			to ifIndex 448."

        ::= { rc2kChassis 13 }

rc2kChassisPortLed3Status  OBJECT-TYPE
        SYNTAX          OCTET STRING (SIZE(512))
        MAX-ACCESS      read-only
        STATUS          current
        DESCRIPTION     "This is applicable only for Tomahawk 100G port. Each 100G port can operate
			with 100G pluggable module or channelized to 4 25G sub-ports, or operate
			with 40G pluggable module or channelized to 4 10G sub-ports. 
	                Each octet string contains the value of a sub-port LED status. And use the
			ifIndex as the position starting from 192th octet. Such 192th octet for 1/1/1,
			193 for 1/1/2, 196 for 1/2/1, so on so forth.

		        The following shows the meaning for each byte:

		        byte value     meaning for activity
		        ---------- -------------------------------------------------------------------------
		  	0	                           : port not valid or not present
			1          Light Off               : admin enabled without pluggable module
			2	   Slow Blinking Green     : admin disable wtih/without 100G pluggable
			3	   Slow Blinking Amber     : admin disable wtih 40G pluggable
			4          Slow Blinking Blue      : admin disable wtih 100G pluggable and channelized
			5          Slow Blinking Pruple    : admin disable wtih 40G pluggable and channelized
		        6	   Solid Green             : link up with 100G pluggable
		 	7	   Solid Amber             : link up with 40G pluggable  
			8 	   Solid Blue              : link up with 25G (channelized of 100G pluggable)
			9          Solid Pruple            : link up with 10G (channelized of 40G pluggable)
			10 	   Random Blinking Green   : link up & activity with 100G speed
			11	   Random Blinking Amber   : link up & activity with 40G speed
			12	   Random Blinking Blue    : link up & activity with 25G speed(channelized
				  	     	    	     of 100G pluggable)
			13         Random Blinking Pruple  : link up & activity with 10G speed(channelized
				  	     	    	     of 40G pluggable)
			  "
        ::= { rc2kChassis 14 }
		    
    
-- 2k CPU Ethernet Port table

rc2kCpuEthernetPortTable OBJECT-TYPE
        SYNTAX        SEQUENCE OF Rc2kCpuEthernetPortEntry
        MAX-ACCESS    not-accessible
        STATUS        current
        DESCRIPTION   "2k CPU Ethernet Port table"
        ::= { rc2k 2 }

rc2kCpuEthernetPortEntry OBJECT-TYPE
        SYNTAX        Rc2kCpuEthernetPortEntry
        MAX-ACCESS    not-accessible
        STATUS        current
        DESCRIPTION   "Entry containing infomation of 2k CPU Ethernet Port"
        INDEX         { rc2kCpuEthernetPortIfIndex }
        ::= { rc2kCpuEthernetPortTable 1 }

Rc2kCpuEthernetPortEntry ::= SEQUENCE {
                rc2kCpuEthernetPortIfIndex       InterfaceIndex,
		rc2kCpuEthernetPortDescr	 DisplayString,
                rc2kCpuEthernetPortAdminStatus   INTEGER,
                rc2kCpuEthernetPortOperStatus    INTEGER,
                rc2kCpuEthernetPortAddr          IpAddress,
                rc2kCpuEthernetPortMask          IpAddress,
                rc2kCpuEthernetPortGateway       IpAddress,
                rc2kCpuEthernetPortNetwork       IpAddress,
                rc2kCpuEthernetPortAutoNegotiate TruthValue,
                rc2kCpuEthernetPortAdminDuplex   INTEGER,
                rc2kCpuEthernetPortOperDuplex    INTEGER,
                rc2kCpuEthernetPortAdminSpeed    INTEGER,
                rc2kCpuEthernetPortOperSpeed     INTEGER,
                rc2kCpuEthernetPortEnableBootp   TruthValue,
                rc2kCpuEthernetPortMgmtMacAddr   MacAddress
        }

rc2kCpuEthernetPortIfIndex OBJECT-TYPE
        SYNTAX        InterfaceIndex
        MAX-ACCESS    read-only
        STATUS        current
        DESCRIPTION   "IfIndex of the port."
        ::= { rc2kCpuEthernetPortEntry 1 }

rc2kCpuEthernetPortDescr OBJECT-TYPE 
        SYNTAX        DisplayString (SIZE (0..128)) 
        MAX-ACCESS    read-only 
        STATUS        current 
        DESCRIPTION   "Port description" 
        ::= { rc2kCpuEthernetPortEntry 2 } 

rc2kCpuEthernetPortAdminStatus OBJECT-TYPE
        SYNTAX        	INTEGER
                      	{
                            up(1),
                            down(2),
                            unknown(3)
                      	}
        MAX-ACCESS        	read-write
        STATUS        	current
        DESCRIPTION  	"Used to configure the admininstrative status
			of the port."
        ::= { rc2kCpuEthernetPortEntry 3 }

rc2kCpuEthernetPortOperStatus OBJECT-TYPE
        SYNTAX        	INTEGER
                      	{
                            up(1),
                            down(2),
                            unknown(3)
                      	}
        MAX-ACCESS        	read-only
        STATUS        	current
        DESCRIPTION   	"Used to indicate the administrative status
			of the port."
        ::= { rc2kCpuEthernetPortEntry 4 }

rc2kCpuEthernetPortAddr OBJECT-TYPE
        SYNTAX        	IpAddress
        MAX-ACCESS        	read-write
        STATUS        	current
        DESCRIPTION   	"Used to configure the port's IP address"
        ::= { rc2kCpuEthernetPortEntry 5 }

rc2kCpuEthernetPortMask OBJECT-TYPE
        SYNTAX        	IpAddress
        MAX-ACCESS        	read-write
        STATUS        	current
        DESCRIPTION   	"Used to configure the port's net mask"
        ::= { rc2kCpuEthernetPortEntry 6 }

rc2kCpuEthernetPortGateway OBJECT-TYPE
        SYNTAX        	IpAddress
        MAX-ACCESS        	read-write
        STATUS        	current
        DESCRIPTION   	"Used to configure the the IP address of the
			gateway that should be used to forward IP
			traffic."  
        ::= { rc2kCpuEthernetPortEntry 7 }

rc2kCpuEthernetPortNetwork OBJECT-TYPE
        SYNTAX        	IpAddress
        MAX-ACCESS        	read-write
        STATUS        	current
        DESCRIPTION   	"Used to configure the network that can be
			used to remotely manage this device."
        ::= { rc2kCpuEthernetPortEntry 8 }

rc2kCpuEthernetPortAutoNegotiate OBJECT-TYPE
        SYNTAX        	TruthValue
        MAX-ACCESS        	read-write
        STATUS        	current
        DESCRIPTION   	"Used to configure auto-negotiation on this
			port."
	DEFVAL	      	{ true }
        ::= { rc2kCpuEthernetPortEntry 9 }

rc2kCpuEthernetPortAdminDuplex OBJECT-TYPE
        SYNTAX        	INTEGER
                      	{
                            half(1),
                            full(2)
                      	}
        MAX-ACCESS        	read-write
        STATUS        	current
        DESCRIPTION   	"Used to configure the administrative duplex
			setting for this port."
        ::= { rc2kCpuEthernetPortEntry 10 }

rc2kCpuEthernetPortOperDuplex OBJECT-TYPE
        SYNTAX        	INTEGER
                      	{
                            half(1),
                            full(2)
                      	}
        MAX-ACCESS        	read-only
        STATUS        	current
        DESCRIPTION   	"Used to indicate the operational duplex
			setting for this port."
        ::= { rc2kCpuEthernetPortEntry 11 }

rc2kCpuEthernetPortAdminSpeed OBJECT-TYPE
        SYNTAX        	INTEGER
                      	{
                            none(0),
                            mbps10(1),      -- 10Mb/s
                            mbps100(2)      -- 100Mb/s
                      	}
        MAX-ACCESS        	read-write
        STATUS        	current
        DESCRIPTION   	"Used to configure the administrative speed
			setting for this port."
        ::= { rc2kCpuEthernetPortEntry 12 }

rc2kCpuEthernetPortOperSpeed OBJECT-TYPE
        SYNTAX        	INTEGER
                      	{
                            none(0),
                            mbps10(1),      -- 10Mb/s
                            mbps100(2),      -- 100Mb/s
                            mbps1000(3)     -- 1000Mb/s
                      	}
        MAX-ACCESS        	read-only
        STATUS        	current
        DESCRIPTION   	"Used to indicate the operational duplex
			setting for this port."
        ::= { rc2kCpuEthernetPortEntry 13 }

rc2kCpuEthernetPortEnableBootp OBJECT-TYPE
        SYNTAX        	TruthValue
        MAX-ACCESS        	read-write
        STATUS        	current
        DESCRIPTION   	"Used to enable/disable the Bootp feature
			on this port."
	DEFVAL	      	{ false }
        ::= { rc2kCpuEthernetPortEntry 14 }

rc2kCpuEthernetPortMgmtMacAddr OBJECT-TYPE
        SYNTAX          MacAddress 
        MAX-ACCESS      read-only 
        STATUS          current 
        DESCRIPTION     "Used to indicate the mac addr for this port."
        ::= { rc2kCpuEthernetPortEntry 15 }


-- 2k CPU Serial Port table

rc2kCpuSerialPortTable OBJECT-TYPE
        SYNTAX        SEQUENCE OF Rc2kCpuSerialPortEntry
        MAX-ACCESS    not-accessible
        STATUS        current
        DESCRIPTION   "2k CPU Serial Port table"
        ::= { rc2k 3 }

rc2kCpuSerialPortEntry OBJECT-TYPE
        SYNTAX        Rc2kCpuSerialPortEntry
        MAX-ACCESS    not-accessible
        STATUS        current
        DESCRIPTION   "Entry containing infomation of 2k CPU Serial Port"
        INDEX         { rc2kCpuSerialPortIfIndex }
        ::= { rc2kCpuSerialPortTable 1 }

Rc2kCpuSerialPortEntry ::= SEQUENCE {
                rc2kCpuSerialPortIfIndex          InterfaceIndex,
		rc2kCpuSerialPortDescr		  DisplayString,
                rc2kCpuSerialPortMode             INTEGER,
                rc2kCpuSerialPortAdminStatus      INTEGER,
                rc2kCpuSerialPortOperStatus       INTEGER,
                rc2kCpuSerialPortBaudRate         INTEGER,
                rc2kCpuSerialPortDataBits         INTEGER,
                rc2kCpuSerialPortMyAddr           IpAddress,
                rc2kCpuSerialPortPeerAddr         IpAddress,
                rc2kCpuSerialPortSlipMtu          INTEGER,
                rc2kCpuSerialPortSlipTxRxCompress TruthValue,
                rc2kCpuSerialPortSlipRxCompress   TruthValue,
                rc2kCpuSerialPortPppConfigFile    OCTET STRING
        }

rc2kCpuSerialPortIfIndex OBJECT-TYPE
        SYNTAX        	InterfaceIndex
        MAX-ACCESS        	read-only
        STATUS        	current
        DESCRIPTION   	"IfIndex for this port."
        ::= { rc2kCpuSerialPortEntry 1 }

rc2kCpuSerialPortDescr OBJECT-TYPE
        SYNTAX        	DisplayString (SIZE (0..128))
        MAX-ACCESS        	read-only
        STATUS        	current
        DESCRIPTION   	"Port description."
        ::= { rc2kCpuSerialPortEntry 2 }

rc2kCpuSerialPortMode OBJECT-TYPE
        SYNTAX        	INTEGER
                      	{
                            cli(1),
                            slip(2),
                            ppp(3)
                     	 }
        MAX-ACCESS        	read-write
        STATUS       	 current
        DESCRIPTION   	"Used to configure the mode this port should
			operate in."
        ::= { rc2kCpuSerialPortEntry 3 }

rc2kCpuSerialPortAdminStatus OBJECT-TYPE
        SYNTAX        	INTEGER
                      	{
                            up(1),
                            down(2),
                            unknown(3)
                      	}
        MAX-ACCESS        	read-write
        STATUS        	current
        DESCRIPTION     "Used to configure the administrative status
                        setting for this port."
        ::= { rc2kCpuSerialPortEntry 4 }

rc2kCpuSerialPortOperStatus OBJECT-TYPE
        SYNTAX        	INTEGER
                      	{
                            up(1),
                            down(2),
                            unknown(3)
                      	}
        MAX-ACCESS        	read-only
        STATUS        	current
        DESCRIPTION     "Used to indicate the operational status
                        setting for this port."
        ::= { rc2kCpuSerialPortEntry 5 }

rc2kCpuSerialPortBaudRate OBJECT-TYPE
        SYNTAX        	INTEGER
                      	{
                            baud2400(2400),
                            baud4800(4800),
                            baud9600(9600),
                            baud19200(19200),
                            baud38400(38400),
                            baud57600(57600),
                            baud115200(115200)
                      	}
        MAX-ACCESS        	read-write
        STATUS        	current
        DESCRIPTION   	"Used to configure the baud rate of this port."
        ::= { rc2kCpuSerialPortEntry 6 }

rc2kCpuSerialPortDataBits OBJECT-TYPE
        SYNTAX        	INTEGER
                      	{
                            seven(1),
                            eight(2)
                      	}
        MAX-ACCESS        	read-write
        STATUS        	current
        DESCRIPTION   	"Used to configure the number of data bits, per
			byte of data, this port should send/receive."
        ::= { rc2kCpuSerialPortEntry 7 }

rc2kCpuSerialPortMyAddr OBJECT-TYPE
        SYNTAX        	IpAddress
        MAX-ACCESS        	read-write
        STATUS        	current
        DESCRIPTION   	"Used to configure this port's IP address.
			Used for both 'slip' and 'ppp' modes."
        ::= { rc2kCpuSerialPortEntry 8 }

rc2kCpuSerialPortPeerAddr OBJECT-TYPE
        SYNTAX        	IpAddress
        MAX-ACCESS        	read-write
        STATUS        	current
        DESCRIPTION   	"Used to configure the peer's IP address.
			Used for both 'slip' and 'ppp' modes."
        ::= { rc2kCpuSerialPortEntry 9 }

rc2kCpuSerialPortSlipMtu OBJECT-TYPE
        SYNTAX        	INTEGER (0..224)
        MAX-ACCESS        	read-write
        STATUS        	current
        DESCRIPTION   	"Used to configure the MTU for this port.
			Used for slip only."
        ::= { rc2kCpuSerialPortEntry 10 }

rc2kCpuSerialPortSlipTxRxCompress OBJECT-TYPE
        SYNTAX        	TruthValue
        MAX-ACCESS        	read-write
        STATUS        	current
        DESCRIPTION   	"Used to enable/disable compression of TCP/IP
			packet headers on this port.  Used for slip only."
	DEFVAL	      	{ true }
        ::= { rc2kCpuSerialPortEntry 11 }

rc2kCpuSerialPortSlipRxCompress OBJECT-TYPE
        SYNTAX        	TruthValue
        MAX-ACCESS        	read-write
        STATUS        	current
        DESCRIPTION   	"Used to enable/disable compression for receiving
			packets on this port.  Used for slip only."	
	DEFVAL	      	{ true }
        ::= { rc2kCpuSerialPortEntry 12 }

rc2kCpuSerialPortPppConfigFile OBJECT-TYPE
        SYNTAX        	OCTET STRING (SIZE(256))
        MAX-ACCESS        	read-write
        STATUS        	current
        DESCRIPTION   	"Used to configure the configuration file to use
			for PPP."
        ::= { rc2kCpuSerialPortEntry 13 }


-- 2k Device Group

rc2kDevice     OBJECT IDENTIFIER ::= { rc2k 4 }

rc2kDeviceGlobalTable OBJECT-TYPE
        SYNTAX        SEQUENCE OF Rc2kDeviceGlobalEntry
        MAX-ACCESS    not-accessible
        STATUS        current
        DESCRIPTION   "2k CPU Ethernet Port table"
        ::= { rc2kDevice 1 }

rc2kDeviceGlobalEntry OBJECT-TYPE
        SYNTAX        Rc2kDeviceGlobalEntry
        MAX-ACCESS    not-accessible
        STATUS        current
        DESCRIPTION   "Entry containing infomation of 2k CPU Ethernet Port"
        INDEX         { rc2kDeviceGlobalSlot }
        ::= { rc2kDeviceGlobalTable 1 }

Rc2kDeviceGlobalEntry ::= SEQUENCE {
		rc2kDeviceGlobalSlot		INTEGER,
		rc2kDeviceGlobalFlashBytesUsed 	Integer32,
		rc2kDeviceGlobalFlashBytesFree 	Integer32,
		rc2kDeviceGlobalFlashNumFiles 	Integer32,
		rc2kDeviceGlobalPcmciaBytesUsed	Integer32,
		rc2kDeviceGlobalPcmciaBytesFree	Integer32,
		rc2kDeviceGlobalPcmciaNumFiles 	Integer32,
		rc2kDeviceGlobalAction 		INTEGER,
		rc2kDeviceGlobalResult 		INTEGER,
		rc2kDeviceGlobalFlash1BytesUsed Integer32,
		rc2kDeviceGlobalFlash1BytesFree Integer32,
		rc2kDeviceGlobalFlash1NumFiles  Integer32,
                rc2kDeviceGlobalUsbBytesUsed    Counter64,   
                rc2kDeviceGlobalUsbBytesFree    Counter64,
                rc2kDeviceGlobalUsbNumFiles     Integer32,
                rc2kDeviceGlobalExtflashBytesUsed       Counter64,
                rc2kDeviceGlobalExtflashBytesFree       Counter64,
                rc2kDeviceGlobalExtflashNumFiles        Integer32,
		rc2kDeviceGlobalIntflashBytesUsed 	Counter64,
		rc2kDeviceGlobalIntflashBytesFree 	Counter64

	}

rc2kDeviceGlobalSlot OBJECT-TYPE
        SYNTAX        INTEGER (1..6)
        MAX-ACCESS    read-only
        STATUS        current
        DESCRIPTION   "slot number"
        ::= { rc2kDeviceGlobalEntry 1 }

rc2kDeviceGlobalFlashBytesUsed OBJECT-TYPE
        SYNTAX        Integer32
        MAX-ACCESS    read-only
        STATUS        current
        DESCRIPTION   "bytes used"
        ::= { rc2kDeviceGlobalEntry 2 }

rc2kDeviceGlobalFlashBytesFree OBJECT-TYPE
        SYNTAX        Integer32
        MAX-ACCESS    read-only
        STATUS        current
        DESCRIPTION   "bytes free"
        ::= { rc2kDeviceGlobalEntry 3 }

rc2kDeviceGlobalFlashNumFiles OBJECT-TYPE
        SYNTAX        Integer32
        MAX-ACCESS    read-only
        STATUS        current
        DESCRIPTION   "# files in flash"
        ::= { rc2kDeviceGlobalEntry 4 }

rc2kDeviceGlobalPcmciaBytesUsed OBJECT-TYPE
        SYNTAX        Integer32
        MAX-ACCESS    read-only
        STATUS        current
        DESCRIPTION   "bytes used"
        ::= { rc2kDeviceGlobalEntry 5 }

rc2kDeviceGlobalPcmciaBytesFree OBJECT-TYPE
        SYNTAX        Integer32
        MAX-ACCESS    read-only
        STATUS        current
        DESCRIPTION   "bytes free"
        ::= { rc2kDeviceGlobalEntry 6 }

rc2kDeviceGlobalPcmciaNumFiles OBJECT-TYPE
        SYNTAX        Integer32
        MAX-ACCESS    read-only
        STATUS        current
        DESCRIPTION   "# files in pcmcia"
        ::= { rc2kDeviceGlobalEntry 7 }
 
rc2kDeviceGlobalAction OBJECT-TYPE
        SYNTAX        INTEGER
                      {
                            none(1),
                            resetPcmcia(2),
                            pcmciaStop(3),
			    pcmciaStart(4)
                      }
        MAX-ACCESS    read-write
        STATUS        current
        DESCRIPTION   "none(1), resetPcmcia(2), .."
        ::= { rc2kDeviceGlobalEntry 8 }

rc2kDeviceGlobalResult OBJECT-TYPE
        SYNTAX        INTEGER {
                            none(1),
                            inProgress(2),
                            success(3),
                            fail(4)
                      }
        MAX-ACCESS    read-only
        STATUS        current
        DESCRIPTION   "Used to indicate the result of the last action
                      performed on one of the system's device."
        ::= { rc2kDeviceGlobalEntry 9 }  
        
rc2kDeviceGlobalFlash1BytesUsed OBJECT-TYPE
        SYNTAX        Integer32
        MAX-ACCESS    read-only
        STATUS        current
        DESCRIPTION   "bytes used"
        ::= { rc2kDeviceGlobalEntry 10 }

rc2kDeviceGlobalFlash1BytesFree OBJECT-TYPE
        SYNTAX        Integer32
        MAX-ACCESS    read-only
        STATUS        current
        DESCRIPTION   "bytes free"
        ::= { rc2kDeviceGlobalEntry 11 }

rc2kDeviceGlobalFlash1NumFiles OBJECT-TYPE
        SYNTAX        Integer32
        MAX-ACCESS    read-only
        STATUS        current
        DESCRIPTION   "# files in flash"
        ::= { rc2kDeviceGlobalEntry 12 }

rc2kDeviceGlobalUsbBytesUsed OBJECT-TYPE
        SYNTAX        Counter64
        MAX-ACCESS    read-only
        STATUS        current
        DESCRIPTION   "bytes used in USB"
        ::= { rc2kDeviceGlobalEntry 13 }

rc2kDeviceGlobalUsbBytesFree OBJECT-TYPE
        SYNTAX        Counter64
        MAX-ACCESS    read-only
        STATUS        current
        DESCRIPTION   "bytes free in USB"
        ::= { rc2kDeviceGlobalEntry 14 }

rc2kDeviceGlobalUsbNumFiles OBJECT-TYPE
        SYNTAX        Integer32
        MAX-ACCESS    read-only
        STATUS        current
        DESCRIPTION   "# files in USB"
        ::= { rc2kDeviceGlobalEntry 15 }

rc2kDeviceGlobalExtflashBytesUsed OBJECT-TYPE
        SYNTAX        Counter64
        MAX-ACCESS    read-only
        STATUS        current
        DESCRIPTION   "bytes used in Extflash"
        ::= { rc2kDeviceGlobalEntry 16 }

rc2kDeviceGlobalExtflashBytesFree OBJECT-TYPE
        SYNTAX        Counter64
        MAX-ACCESS    read-only
        STATUS        current
        DESCRIPTION   "bytes free in Extflash"
        ::= { rc2kDeviceGlobalEntry 17 }

rc2kDeviceGlobalExtflashNumFiles OBJECT-TYPE
        SYNTAX        Integer32
        MAX-ACCESS    read-only
        STATUS        current
        DESCRIPTION   "# files in Extflash"
        ::= { rc2kDeviceGlobalEntry 18 }
    
rc2kDeviceGlobalIntflashBytesUsed OBJECT-TYPE
        SYNTAX        Counter64
        MAX-ACCESS    read-only
        STATUS        current
        DESCRIPTION   "bytes used in intflash. It is used to
	               replace rc2kDeviceGlobalFlashBytesUsed"
        ::= { rc2kDeviceGlobalEntry 19 }

rc2kDeviceGlobalIntflashBytesFree OBJECT-TYPE
        SYNTAX        Counter64
        MAX-ACCESS    read-only
        STATUS        current
        DESCRIPTION   "bytes free in intflash. It is used to
	               replace rc2kDeviceGlobalFlashByteFree"
        ::= { rc2kDeviceGlobalEntry 20 }

-- 2k Device Separator1 
 
rc2kDeviceSeparator1 OBJECT-TYPE
        SYNTAX        	Integer32
        MAX-ACCESS        	read-only
        STATUS        	current
        DESCRIPTION   	"This leaf is used to provide a separation between
			tables.  No meaningful information is stored in this
			variable." 
        ::= { rc2kDevice 2 }

 
-- 2k Device Flash File table

rc2kDeviceFlashFileTable OBJECT-TYPE
        SYNTAX        SEQUENCE OF Rc2kDeviceFlashFileEntry
        MAX-ACCESS    not-accessible
        STATUS        current
        DESCRIPTION   "2k Flash table"
        ::= { rc2kDevice 3 }

rc2kDeviceFlashFileEntry OBJECT-TYPE
        SYNTAX        Rc2kDeviceFlashFileEntry
        MAX-ACCESS    not-accessible
        STATUS        current
        DESCRIPTION   "Entry containing infomation of 2k CPU Serial Port"
        INDEX         { rc2kDeviceFlashFileSlot, rc2kDeviceFlashFileName }
        ::= { rc2kDeviceFlashFileTable 1 }

Rc2kDeviceFlashFileEntry ::= SEQUENCE {
                rc2kDeviceFlashFileSlot	INTEGER,
                rc2kDeviceFlashFileName DisplayString,
                rc2kDeviceFlashFileDate DisplayString,
                rc2kDeviceFlashFileSize Integer32
        }

rc2kDeviceFlashFileSlot OBJECT-TYPE
        SYNTAX        INTEGER (1..6) 
        MAX-ACCESS    read-only
        STATUS        current
        DESCRIPTION   "slot number"
        ::= { rc2kDeviceFlashFileEntry 1 }

rc2kDeviceFlashFileName OBJECT-TYPE
        SYNTAX        DisplayString (SIZE(0..255))
        MAX-ACCESS    read-only
        STATUS        current
        DESCRIPTION   "name of file"
        ::= { rc2kDeviceFlashFileEntry 2 }

rc2kDeviceFlashFileDate OBJECT-TYPE
        SYNTAX        DisplayString (SIZE(0..32))
        MAX-ACCESS    read-only
        STATUS        current
        DESCRIPTION   "date"
        ::= { rc2kDeviceFlashFileEntry 3 }

rc2kDeviceFlashFileSize OBJECT-TYPE
        SYNTAX        Integer32
        MAX-ACCESS    read-only
        STATUS        current
        DESCRIPTION   "size in bytes"
        ::= { rc2kDeviceFlashFileEntry 4 }

-- 2k Device Pcmcia present

rc2kDevicePcmciaPresent OBJECT-TYPE
        SYNTAX        TruthValue
        MAX-ACCESS    read-only
        STATUS        current
        DESCRIPTION   "pcmcia is a slower device. This leaf is used to
                       stop the access into pcmcia file table when it
                       got the end of flash file table."
        ::= { rc2kDevice 4 }

-- 2k Device Pcmcia File table

rc2kDevicePcmciaFileTable OBJECT-TYPE
        SYNTAX        SEQUENCE OF Rc2kDevicePcmciaFileEntry
        MAX-ACCESS    not-accessible
        STATUS        current
        DESCRIPTION   "2k PCMCIA table"
        ::= { rc2kDevice 5 }

rc2kDevicePcmciaFileEntry OBJECT-TYPE
        SYNTAX        Rc2kDevicePcmciaFileEntry
        MAX-ACCESS    not-accessible
        STATUS        current
        DESCRIPTION   "Entry containing infomation of 2k CPU Serial Port"
        INDEX         { rc2kDevicePcmciaFileSlot, rc2kDevicePcmciaFileName }
        ::= { rc2kDevicePcmciaFileTable 1 }

Rc2kDevicePcmciaFileEntry ::= SEQUENCE {
                rc2kDevicePcmciaFileSlot INTEGER,
                rc2kDevicePcmciaFileName DisplayString,
                rc2kDevicePcmciaFileDate DisplayString,
                rc2kDevicePcmciaFileSize Integer32
        }

rc2kDevicePcmciaFileSlot OBJECT-TYPE
        SYNTAX        INTEGER (3 | 5..6)
        MAX-ACCESS    read-only
        STATUS        current
        DESCRIPTION   "slot number"
        ::= { rc2kDevicePcmciaFileEntry 1 }

rc2kDevicePcmciaFileName OBJECT-TYPE
        SYNTAX        DisplayString (SIZE(0..255))
        MAX-ACCESS    read-only
        STATUS        current
        DESCRIPTION   "name of file"
        ::= { rc2kDevicePcmciaFileEntry 2 }

rc2kDevicePcmciaFileDate OBJECT-TYPE
        SYNTAX        DisplayString (SIZE(0..32))
        MAX-ACCESS    read-only
        STATUS        current
        DESCRIPTION   "date"
        ::= { rc2kDevicePcmciaFileEntry 3 }

rc2kDevicePcmciaFileSize OBJECT-TYPE
        SYNTAX        Integer32
        MAX-ACCESS    read-only
        STATUS        current
        DESCRIPTION   "size in bytes"
        ::= { rc2kDevicePcmciaFileEntry 4 }

-- 2k Device Separator2

rc2kDeviceSeparator2 OBJECT-TYPE 
        SYNTAX          Integer32
        MAX-ACCESS      read-only 
        STATUS          current 
        DESCRIPTION     "This leaf is used to provide a separation between 
                        tables.  No meaningful information is stored in this
                        variable."
        ::= { rc2kDevice 6 } 

-- 2k Device Flash1 present

rc2kDeviceFlash1Present OBJECT-TYPE
        SYNTAX        TruthValue
        MAX-ACCESS    read-only
        STATUS        current
        DESCRIPTION   "This leaf is used to stop the access into Flash1
                       file table."
        ::= { rc2kDevice 7 }

-- 2k Device Flash1 File table

rc2kDeviceFlash1FileTable OBJECT-TYPE
        SYNTAX        SEQUENCE OF Rc2kDeviceFlash1FileEntry
        MAX-ACCESS    not-accessible
        STATUS        current
        DESCRIPTION   "2k Flash1 table"
        ::= { rc2kDevice 8 }

rc2kDeviceFlash1FileEntry OBJECT-TYPE
        SYNTAX        Rc2kDeviceFlash1FileEntry
        MAX-ACCESS    not-accessible
        STATUS        current
        DESCRIPTION   "Entry containing infomation of 2k Flash1 Files"
        INDEX         { rc2kDeviceFlash1FileSlot, rc2kDeviceFlash1FileName }
        ::= { rc2kDeviceFlash1FileTable 1 }

Rc2kDeviceFlash1FileEntry ::= SEQUENCE {
                rc2kDeviceFlash1FileSlot INTEGER,
                rc2kDeviceFlash1FileName DisplayString,
                rc2kDeviceFlash1FileDate DisplayString,
                rc2kDeviceFlash1FileSize Integer32
        }

rc2kDeviceFlash1FileSlot OBJECT-TYPE
        SYNTAX        INTEGER (5..6)
        MAX-ACCESS    read-only
        STATUS        current
        DESCRIPTION   "slot number"
        ::= { rc2kDeviceFlash1FileEntry 1 }

rc2kDeviceFlash1FileName OBJECT-TYPE
        SYNTAX        DisplayString (SIZE(0..255))
        MAX-ACCESS    read-only
        STATUS        current
        DESCRIPTION   "name of file"
        ::= { rc2kDeviceFlash1FileEntry 2 }

rc2kDeviceFlash1FileDate OBJECT-TYPE
        SYNTAX        DisplayString (SIZE(0..32))
        MAX-ACCESS    read-only
        STATUS        current
        DESCRIPTION   "date"
        ::= { rc2kDeviceFlash1FileEntry 3 }

rc2kDeviceFlash1FileSize OBJECT-TYPE
        SYNTAX        Integer32
        MAX-ACCESS    read-only
        STATUS        current
        DESCRIPTION   "size in bytes"
        ::= { rc2kDeviceFlash1FileEntry 4 }

-- 2k Device Extflash File table

rc2kDeviceExtflashFileTable OBJECT-TYPE
        SYNTAX        SEQUENCE OF Rc2kDeviceExtflashFileEntry
        MAX-ACCESS    not-accessible
        STATUS        current
        DESCRIPTION   "2k Flash table"
        ::= { rc2kDevice 9}

rc2kDeviceExtflashFileEntry OBJECT-TYPE
        SYNTAX        Rc2kDeviceExtflashFileEntry
        MAX-ACCESS    not-accessible
        STATUS        current
        DESCRIPTION   "Entry containing information of extflash files"
        INDEX         { rc2kDeviceExtflashFileSlot,
                        IMPLIED rc2kDeviceExtflashFileName }
        ::= { rc2kDeviceExtflashFileTable 1 }

Rc2kDeviceExtflashFileEntry ::= SEQUENCE {
                rc2kDeviceExtflashFileSlot Integer32,
                rc2kDeviceExtflashFileName DisplayString,
                rc2kDeviceExtflashFileDate DisplayString,
                rc2kDeviceExtflashFileSize Unsigned32
        }

rc2kDeviceExtflashFileSlot OBJECT-TYPE
        SYNTAX        Integer32 (1..2)
        MAX-ACCESS    not-accessible
        STATUS        current
        DESCRIPTION   "slot number"
        ::= { rc2kDeviceExtflashFileEntry 1 }

rc2kDeviceExtflashFileName OBJECT-TYPE
        SYNTAX        DisplayString (SIZE(1..114))
        MAX-ACCESS    not-accessible
        STATUS        current
        DESCRIPTION   "name of file"
        ::= { rc2kDeviceExtflashFileEntry 2 }

rc2kDeviceExtflashFileDate OBJECT-TYPE
        SYNTAX        DisplayString (SIZE(0..32))
        MAX-ACCESS    read-only
        STATUS        current
        DESCRIPTION   "date"
        ::= { rc2kDeviceExtflashFileEntry 3 }

rc2kDeviceExtflashFileSize OBJECT-TYPE
        SYNTAX        Unsigned32
        MAX-ACCESS    read-only
        STATUS        current
        DESCRIPTION   "size in bytes"
        ::= { rc2kDeviceExtflashFileEntry 4 }

-- 2k Device USB File table

rc2kDeviceUsbFileTable OBJECT-TYPE
        SYNTAX        SEQUENCE OF Rc2kDeviceUsbFileEntry
        MAX-ACCESS    not-accessible
        STATUS        current
        DESCRIPTION   "2k Usb table"
        ::= { rc2kDevice 10 }

rc2kDeviceUsbFileEntry OBJECT-TYPE
        SYNTAX        Rc2kDeviceUsbFileEntry
        MAX-ACCESS    not-accessible
        STATUS        current
        DESCRIPTION   "Entry containing information of USB files"
        INDEX         { rc2kDeviceUsbFileSlot,
                        IMPLIED rc2kDeviceUsbFileName }
        ::= { rc2kDeviceUsbFileTable 1 }

Rc2kDeviceUsbFileEntry ::= SEQUENCE {
                rc2kDeviceUsbFileSlot Integer32,
                rc2kDeviceUsbFileName DisplayString,
                rc2kDeviceUsbFileDate DisplayString,
                rc2kDeviceUsbFileSize Unsigned32
        }

rc2kDeviceUsbFileSlot OBJECT-TYPE
        SYNTAX        Integer32 (0..8)
        MAX-ACCESS    not-accessible
        STATUS        current
        DESCRIPTION   "slot number"
        ::= { rc2kDeviceUsbFileEntry 1 }

rc2kDeviceUsbFileName OBJECT-TYPE
        SYNTAX        DisplayString (SIZE(1..114))
        MAX-ACCESS    not-accessible
        STATUS        current
        DESCRIPTION   "name of file"
        ::= { rc2kDeviceUsbFileEntry 2 }

rc2kDeviceUsbFileDate OBJECT-TYPE
        SYNTAX        DisplayString (SIZE(0..32))
        MAX-ACCESS    read-only
        STATUS        current
        DESCRIPTION   "date"
        ::= { rc2kDeviceUsbFileEntry 3 }

rc2kDeviceUsbFileSize OBJECT-TYPE
        SYNTAX        Unsigned32
        MAX-ACCESS    read-only
        STATUS        current
        DESCRIPTION   "size in bytes"
        ::= { rc2kDeviceUsbFileEntry 4 }

-- 2k Boot Config Table

rc2kBootConfigTable OBJECT-TYPE
        SYNTAX        SEQUENCE OF Rc2kBootConfigEntry
        MAX-ACCESS    not-accessible
        STATUS        current
        DESCRIPTION   "2k Boot Configuration table"
        ::= { rc2k 5 }

rc2kBootConfigEntry OBJECT-TYPE
        SYNTAX        Rc2kBootConfigEntry
        MAX-ACCESS    not-accessible
        STATUS        current
        DESCRIPTION   "Entry containing boot configuration information."
        INDEX         { rc2kBootConfigSlot }
        ::= { rc2kBootConfigTable 1 }

Rc2kBootConfigEntry ::= SEQUENCE {
		rc2kBootConfigSlot 			INTEGER,
		rc2kBootConfigLastBootConfigSource	DisplayString,
		rc2kBootConfigLastRuntimeImageSource	DisplayString,
		rc2kBootConfigLastRuntimeConfigSource	DisplayString,
		rc2kBootConfigPrimaryImageSource	DisplayString,
		rc2kBootConfigPrimaryConfigSource	DisplayString,
		rc2kBootConfigSecondaryImageSource	DisplayString,
		rc2kBootConfigSecondaryConfigSource	DisplayString,
		rc2kBootConfigTertiaryImageSource	DisplayString,
		rc2kBootConfigTertiaryConfigSource	DisplayString,
		rc2kBootConfigEnableAutoBoot		TruthValue,
		rc2kBootConfigEnableFactoryDefaults	TruthValue,
		rc2kBootConfigEnableDebugMode	TruthValue,
		rc2kBootConfigEnableHwWatchDogTimer	TruthValue,
		rc2kBootConfigEnableRebootOnError	TruthValue,
		rc2kBootConfigEnableTelnetServer	TruthValue,
		rc2kBootConfigEnableRloginServer	TruthValue,
		rc2kBootConfigEnableFtpServer	TruthValue,
		rc2kBootConfigEnableTftpServer	TruthValue,
		rc2kBootConfigSwVersion		DisplayString,
		rc2kBootConfigMulticastConfigProfile    	INTEGER,
		rc2kBootConfigEnableSshServer	TruthValue,
	        rc2kBootConfigEnableAltLed              	TruthValue,
	        rc2kBootConfigPrimaryBackupConfigSource   DisplayString,
               	rc2kBootConfigSecondaryBackupConfigSource DisplayString,
                rc2kBootConfigTertiaryBackupConfigSource  DisplayString,
                rc2kBootConfigEnable8616ReAutoneg	TruthValue,
                rc2kBootConfigMezzImageSource	        DisplayString,
                rc2kBootConfigEnableMezz               	TruthValue,
                rc2kBootConfigPrimaryLicenseSource               DisplayString,
                rc2kBootConfigSecondaryLicenseSource        DisplayString,
                rc2kBootConfigTertiaryLicenseSource               DisplayString,
                rc2kBootConfigUnknownDstMacDiscard            TruthValue, --obsolete
                rc2kBootConfigUnknownDstMacDiscardOperStatus  INTEGER,     --obsolete
                rc2kBootConfigEnableAutoAssignIp              TruthValue,
                rc2kBootConfigUpgradeBootImageSource         DisplayString,
                rc2kBootConfigUpgradeRuntimeImageSource      DisplayString,
                rc2kBootConfigUpgradeMezzImageSource         DisplayString,
                rc2kBootConfigUpgradeConfigSource            DisplayString,
                rc2kBootConfigUpgradeRModImageSource         DisplayString,
                rc2kBootConfigUpgradeRCModImageSource        DisplayString,
                rc2kBootConfigUpgradeESMImageSource          DisplayString,
                rc2kBootConfigFallBackBootImageSource        DisplayString,
                rc2kBootConfigEnableCfPcCompat               TruthValue,
                rc2kBootConfigLinecardCompatibilityMode      INTEGER,
		rc2kBootConfigEnableSpbmConfigMode           TruthValue,
		rc2kBootConfigEnableIpv6Mode                 TruthValue,
		rc2kBootConfigEnableEnhancedsecureMode       INTEGER,
		rc2kBootConfigUrpfModeEnable                 TruthValue,
		rc2kBootConfigEnableFlowControlMode  	     TruthValue,
		rc2kBootConfigAdvancedFeatureBwReservation   INTEGER,
		rc2kBootConfigEnableVxlanGwFullInterworkingMode  TruthValue,
		rc2kBootConfigNniMstp                        TruthValue,
		rc2kBootConfigEnableDvrLeafMode              TruthValue,
		rc2kBootConfigEnableVrfScaling               TruthValue,
		rc2kBootConfigLinerateDirectedBroadcast      TruthValue,
                rc2kBootConfigVcMode                         TruthValue,
		rc2kBootConfigEnableIpv6EgressFilterMode     TruthValue,
		rc2kBootConfigEnableSyslogRfc5424Format      TruthValue,
	        rc2kBootConfigEnableFactoryDefaultsMode      INTEGER
        }

rc2kBootConfigSlot OBJECT-TYPE
        SYNTAX        INTEGER (1..11)
        MAX-ACCESS    read-only
        STATUS        current
        DESCRIPTION   "slot number, tattoo use 3 as cpu slot,  
                      4 & 7-10 are not valid cpu slot number,
                      VSP uses slots 1 and 2 for cpu slot"
        ::= { rc2kBootConfigEntry 1 }

rc2kBootConfigLastBootConfigSource OBJECT-TYPE
        SYNTAX        DisplayString (SIZE(0..255))
        MAX-ACCESS    read-only
        STATUS        current
        DESCRIPTION   "boot config source"
        ::= { rc2kBootConfigEntry 2 }

rc2kBootConfigLastRuntimeImageSource OBJECT-TYPE
        SYNTAX        DisplayString (SIZE(0..255))
        MAX-ACCESS    read-only
        STATUS        current
        DESCRIPTION   "runtime image source"
        ::= { rc2kBootConfigEntry 3 }

rc2kBootConfigLastRuntimeConfigSource OBJECT-TYPE
        SYNTAX        DisplayString (SIZE(0..255))
        MAX-ACCESS    read-only
        STATUS        current
        DESCRIPTION   "runtime config source"
        ::= { rc2kBootConfigEntry 4 }

rc2kBootConfigPrimaryImageSource OBJECT-TYPE
        SYNTAX        DisplayString (SIZE(0..255))
        MAX-ACCESS    read-write
        STATUS        current
        DESCRIPTION   "image source"
        ::= { rc2kBootConfigEntry 5 }

rc2kBootConfigPrimaryConfigSource OBJECT-TYPE
        SYNTAX        DisplayString (SIZE(0..255))
        MAX-ACCESS    read-write
        STATUS        current
        DESCRIPTION   "config source"
        ::= { rc2kBootConfigEntry 6 }

rc2kBootConfigSecondaryImageSource OBJECT-TYPE
        SYNTAX        DisplayString (SIZE(0..255))
        MAX-ACCESS    read-write
        STATUS        current
        DESCRIPTION   "image source"
        ::= { rc2kBootConfigEntry 7 }

rc2kBootConfigSecondaryConfigSource OBJECT-TYPE
        SYNTAX        DisplayString (SIZE(0..255))
        MAX-ACCESS    read-write
        STATUS        current
        DESCRIPTION   "config source"
        ::= { rc2kBootConfigEntry 8 }
 
rc2kBootConfigTertiaryImageSource OBJECT-TYPE
        SYNTAX        DisplayString (SIZE(0..255))
        MAX-ACCESS    read-write
        STATUS        current
        DESCRIPTION   "image source"
        ::= { rc2kBootConfigEntry 9 }
 
rc2kBootConfigTertiaryConfigSource OBJECT-TYPE
        SYNTAX        DisplayString (SIZE(0..255))
        MAX-ACCESS    read-write
        STATUS        current
        DESCRIPTION   "config source"
        ::= { rc2kBootConfigEntry 10 }
 
rc2kBootConfigEnableAutoBoot OBJECT-TYPE
        SYNTAX        TruthValue
        MAX-ACCESS    read-write
        STATUS        current
        DESCRIPTION   "auto boot mode"
        ::= { rc2kBootConfigEntry 11 }

rc2kBootConfigEnableFactoryDefaults OBJECT-TYPE
        SYNTAX        TruthValue
        MAX-ACCESS    read-write
        STATUS        current
        DESCRIPTION   "use factory default"
        ::= { rc2kBootConfigEntry 12 }

rc2kBootConfigEnableDebugMode OBJECT-TYPE
        SYNTAX        TruthValue
        MAX-ACCESS    read-write
        STATUS        current
        DESCRIPTION   "debug mode"
        ::= { rc2kBootConfigEntry 13 }

rc2kBootConfigEnableHwWatchDogTimer OBJECT-TYPE
        SYNTAX        TruthValue
        MAX-ACCESS    read-write
        STATUS        current
        DESCRIPTION   "hw watch dog timer"
        ::= { rc2kBootConfigEntry 14 }

rc2kBootConfigEnableRebootOnError OBJECT-TYPE
        SYNTAX        TruthValue
        MAX-ACCESS    read-write
        STATUS        current
        DESCRIPTION   "reboot on error"
        ::= { rc2kBootConfigEntry 15 }

rc2kBootConfigEnableTelnetServer OBJECT-TYPE
        SYNTAX        TruthValue
        MAX-ACCESS    read-write
        STATUS        current
        DESCRIPTION   "telnet server"
        ::= { rc2kBootConfigEntry 16 }

rc2kBootConfigEnableRloginServer OBJECT-TYPE
        SYNTAX        TruthValue
        MAX-ACCESS    read-write
        STATUS        current
        DESCRIPTION   "rlogin server"
        ::= { rc2kBootConfigEntry 17 }

rc2kBootConfigEnableFtpServer OBJECT-TYPE
        SYNTAX        TruthValue
        MAX-ACCESS    read-write
        STATUS        current
        DESCRIPTION   "ftp server"
        ::= { rc2kBootConfigEntry 18 }

rc2kBootConfigEnableTftpServer OBJECT-TYPE
        SYNTAX        TruthValue
        MAX-ACCESS    read-write
        STATUS        current
        DESCRIPTION   "tftp server"
        ::= { rc2kBootConfigEntry 19 }

rc2kBootConfigSwVersion OBJECT-TYPE
        SYNTAX        DisplayString
        MAX-ACCESS    read-only
        STATUS        current
        DESCRIPTION   "current sw version"
        ::= { rc2kBootConfigEntry 20 }
 
rc2kBootConfigMulticastConfigProfile OBJECT-TYPE
        SYNTAX        INTEGER (1..6)
        MAX-ACCESS    read-only
        STATUS        current
        DESCRIPTION   "multicast config"
        DEFVAL        { 1 }
        ::= { rc2kBootConfigEntry 21 }

rc2kBootConfigEnableSshServer OBJECT-TYPE
        SYNTAX        TruthValue
        MAX-ACCESS    read-write
        STATUS        current
        DESCRIPTION   "ssh server"
        ::= { rc2kBootConfigEntry 22 }

rc2kBootConfigEnableAltLed OBJECT-TYPE
        SYNTAX        TruthValue
        MAX-ACCESS    read-write
        STATUS        current
        DESCRIPTION   "Boot flag for enableing Alternate LED"
        ::= { rc2kBootConfigEntry 23 }

rc2kBootConfigPrimaryBackupConfigSource OBJECT-TYPE
        SYNTAX        DisplayString (SIZE(0..255))
        MAX-ACCESS    read-write
        STATUS        current
        DESCRIPTION   "primary backup config source (save config)"
        ::= { rc2kBootConfigEntry 24 }

rc2kBootConfigSecondaryBackupConfigSource OBJECT-TYPE
        SYNTAX        DisplayString (SIZE(0..255))
        MAX-ACCESS    read-write
        STATUS        current
        DESCRIPTION   "secondary backup config source (save config)"
        ::= { rc2kBootConfigEntry 25 }

rc2kBootConfigTertiaryBackupConfigSource OBJECT-TYPE
        SYNTAX        DisplayString (SIZE(0..255))
        MAX-ACCESS    read-write
        STATUS        current
        DESCRIPTION   "tertiary backup config source (save config)"
        ::= { rc2kBootConfigEntry 26 }

rc2kBootConfigEnable8616ReAutoneg OBJECT-TYPE
        SYNTAX        TruthValue
        MAX-ACCESS    read-write
        STATUS        current
        DESCRIPTION   "Enable re-autoneg for 8616SX Cards (Intel GMAC fix)"
        ::= { rc2kBootConfigEntry 27 }

rc2kBootConfigMezzImageSource OBJECT-TYPE
        SYNTAX        DisplayString (SIZE(0..255))
        MAX-ACCESS    read-write
        STATUS        current
        DESCRIPTION   "Mezz image source"
        ::= { rc2kBootConfigEntry 28 }

rc2kBootConfigEnableMezz OBJECT-TYPE
        SYNTAX        TruthValue
        MAX-ACCESS    read-write
        STATUS        current
        DESCRIPTION   "Enable/disable Mezz Flag"
        ::= { rc2kBootConfigEntry 29 }

rc2kBootConfigPrimaryLicenseSource OBJECT-TYPE
        SYNTAX        DisplayString (SIZE(0..255))
        MAX-ACCESS    read-write
        STATUS        current
        DESCRIPTION   "Primary choice for the license source"
        ::= { rc2kBootConfigEntry 30 }

rc2kBootConfigSecondaryLicenseSource OBJECT-TYPE
        SYNTAX        DisplayString (SIZE(0..255))
        MAX-ACCESS    read-write
        STATUS        current
        DESCRIPTION   "Secondary choice for the license source"
        ::= { rc2kBootConfigEntry 31 } 

rc2kBootConfigTertiaryLicenseSource OBJECT-TYPE
        SYNTAX        DisplayString (SIZE(0..255))
        MAX-ACCESS    read-write
        STATUS        current
        DESCRIPTION   "Tertiary choice for the license source"
        ::= { rc2kBootConfigEntry 32 }

rc2kBootConfigUnknownDstMacDiscard OBJECT-TYPE
        SYNTAX        TruthValue
        MAX-ACCESS    read-write
        STATUS        obsolete
        DESCRIPTION   "Enable/disable to discard the unknown destination
		 mac address.  A device reboot is required for the 
		 change to take effect."
        ::= { rc2kBootConfigEntry 33 }

rc2kBootConfigUnknownDstMacDiscardOperStatus OBJECT-TYPE
        SYNTAX        INTEGER {
                        enable(1),
                        disable(2)
                      }		
        MAX-ACCESS    read-only
        STATUS        obsolete
        DESCRIPTION   "Indicates the device operational status of unknown 
		destination mac discard."
        ::= { rc2kBootConfigEntry 34 }

rc2kBootConfigEnableAutoAssignIp OBJECT-TYPE
        SYNTAX        TruthValue
        MAX-ACCESS    read-write
        STATUS        current
        DESCRIPTION   "Enable/disable auto-assign-ip feature"
        ::= { rc2kBootConfigEntry 35}                                          

rc2kBootConfigUpgradeBootImageSource         OBJECT-TYPE
        SYNTAX        DisplayString (SIZE(0..255))
        MAX-ACCESS    read-write
        STATUS        current
        DESCRIPTION   "Upgrade boot image source"
        ::= { rc2kBootConfigEntry 36 }

rc2kBootConfigUpgradeRuntimeImageSource      OBJECT-TYPE
        SYNTAX        DisplayString (SIZE(0..255))
        MAX-ACCESS    read-write
        STATUS        current
        DESCRIPTION   "Upgrade runtime image source"
        ::= { rc2kBootConfigEntry 37 }

rc2kBootConfigUpgradeMezzImageSource         OBJECT-TYPE
        SYNTAX        DisplayString (SIZE(0..255))
        MAX-ACCESS    read-write
        STATUS        current
        DESCRIPTION   "Upgrade mezz image source"
        ::= { rc2kBootConfigEntry 38 }

rc2kBootConfigUpgradeConfigSource            OBJECT-TYPE
        SYNTAX        DisplayString (SIZE(0..255))
        MAX-ACCESS    read-write
        STATUS        current
        DESCRIPTION   "Upgrade config source"
        ::= { rc2kBootConfigEntry 39 }

rc2kBootConfigUpgradeRModImageSource         OBJECT-TYPE
        SYNTAX        DisplayString (SIZE(0..255))
        MAX-ACCESS    read-write
        STATUS        current
        DESCRIPTION   "upgrade RMod image source"
        ::= { rc2kBootConfigEntry 40 }

rc2kBootConfigUpgradeRCModImageSource        OBJECT-TYPE
        SYNTAX        DisplayString (SIZE(0..255))
        MAX-ACCESS    read-write
        STATUS        current
        DESCRIPTION   "upgrade RCMod image source"
        ::= { rc2kBootConfigEntry 41 }

rc2kBootConfigUpgradeESMImageSource          OBJECT-TYPE
        SYNTAX        DisplayString (SIZE(0..255))
        MAX-ACCESS    read-write
        STATUS        current
        DESCRIPTION   "upgrade ESM image source"
        ::= { rc2kBootConfigEntry 42 }

rc2kBootConfigFallBackBootImageSource        OBJECT-TYPE
        SYNTAX        DisplayString (SIZE(0..255))
        MAX-ACCESS    read-write
        STATUS        current
        DESCRIPTION   "upgrade fall-back boot monitor source"
        ::= { rc2kBootConfigEntry 43 }

rc2kBootConfigEnableCfPcCompat        OBJECT-TYPE
        SYNTAX        TruthValue 
        MAX-ACCESS    read-write
        STATUS        current
        DESCRIPTION   "Enable/disable CF PC compatibility"
        ::= { rc2kBootConfigEntry 44 }

rc2kBootConfigLinecardCompatibilityMode OBJECT-TYPE
        SYNTAX        INTEGER {
                        gen1(1),
                        gen2(2)
                      }
        MAX-ACCESS    read-write
        STATUS        current
        DESCRIPTION   "This indicates the compatibility mode of the IO cards
                       on the Chassis. In gen1 mode, both the generation 1
		       cards and generation 2 (ROF) cards will be supported
		       and the max number of FIB records will be set to 500K.
		       In gen2 mode, only the generation 2 (ROF) card will be
		       supported and the gen 1 cards will be powered down. 
		       The max number of FIB records in this mode will be 
		       set to 1 million"
        DEFVAL         { gen1 }
        ::= { rc2kBootConfigEntry 45 }
    
rc2kBootConfigEnableSpbmConfigMode OBJECT-TYPE
        SYNTAX        TruthValue
        MAX-ACCESS    read-write
        STATUS        current
        DESCRIPTION   "Enables spbm-config-mode boot flag. When this flag
	               is true, SPBM configurations are allowed and PIM
		       configurations are disabled and not allowed.
		       When this flag is false, PIM configurations
		       are allowed and SPBM configurations are disabled
		       and not allowed. Changing this flag will reboot
		       the box and it will come up with the selected
		       configuration mode."
        DEFVAL        { true }
        ::= { rc2kBootConfigEntry 46}
    
rc2kBootConfigEnableIpv6Mode OBJECT-TYPE
        SYNTAX        TruthValue
        MAX-ACCESS    read-write
        STATUS        current
        DESCRIPTION   "Enable/disable Ipv6-Mode Flag.This flag is
                       used only for VSP8200 and VSP4k because of the
                       limitation in Trident2 where Ipv6 route with
                       prefix-length >64 cannot be stored in the L3_defip
                       table.Setting of this flag will combine both the TCAM's
                       to store routes with prefix-length >64."
        ::= { rc2kBootConfigEntry 47 }
    
rc2kBootConfigEnableEnhancedsecureMode OBJECT-TYPE
        SYNTAX        INTEGER {
                        jitc(1), 
                        disable(2),
                        non-jitc(3)
                      }
        MAX-ACCESS    read-write
        STATUS        current
        DESCRIPTION   "Enable/disable Federal Mode Flag"
        ::= { rc2kBootConfigEntry 48 }
    
rc2kBootConfigUrpfModeEnable OBJECT-TYPE
        SYNTAX        TruthValue
        MAX-ACCESS    read-write
        STATUS        current
        DESCRIPTION   "From VOSS5.x onwards, unicast reverse path
	    	       forwarding will be supported on small system
		       platforms only if this flag is enabled."
	DEFVAL        { false }
        ::= { rc2kBootConfigEntry 49 }
    
rc2kBootConfigEnableFlowControlMode OBJECT-TYPE
        SYNTAX        TruthValue
        MAX-ACCESS    read-write
        STATUS        current
        DESCRIPTION   "Enable/disable Flow Control Mode Flag."
        ::= { rc2kBootConfigEntry 50 }
	
rc2kBootConfigAdvancedFeatureBwReservation OBJECT-TYPE
        SYNTAX       INTEGER {
                         disable(1),
                         high(2)
--                         low(3)
                      }
        MAX-ACCESS    read-write
        STATUS        current
        DESCRIPTION   "Allow to enable the port forwarding bandwidth working
                      as loopback ports to support advanced feature mode,
                      or disable the reservation for full port mode. Enable can be
                      in levels of high and low. In level of high, the system
                      reserves the maximum bandwidth allowance for the advanced 
                      features. In level of low, the bandwidth is lesser then maximum
                      allowance. This configuration is currently only support for 
                      platform DSG8032, vsp4k and vsp8k platfroms does not support this.
                      Only disable and high are supported in the initial release VOSS 4.3. 
                      Low will be supported in the VOSS 4.4 release."
        ::= { rc2kBootConfigEntry 51 }
    
rc2kBootConfigEnableVxlanGwFullInterworkingMode OBJECT-TYPE
        SYNTAX        TruthValue
        MAX-ACCESS    read-write
        STATUS        current
        DESCRIPTION   "Enables vxlan gateway full interworking mode."
        DEFVAL        { false }
        ::= { rc2kBootConfigEntry 52 }
    
rc2kBootConfigNniMstp OBJECT-TYPE
        SYNTAX        TruthValue
        MAX-ACCESS    read-write
        STATUS        current
        DESCRIPTION   "Flag to decide whether configuration of mstp and other
	    	       vlans on the NNI is allowed. Default is not allowed."
        DEFVAL        { false }
        ::= { rc2kBootConfigEntry 53 }
    
rc2kBootConfigEnableDvrLeafMode OBJECT-TYPE
        SYNTAX        TruthValue
        MAX-ACCESS    read-write
        STATUS        current
        DESCRIPTION   "DVR can be configured as controller or leaf. IP
	               related configuration and show commands are not
		       allowed on leaf. dvr-leaf-mode flag has to be	
                       enabled first before user can configure as DVR leaf.
		       When boot up with this flag enabled, IP related
		       configuration and show commands are hidden. All
		       non DVR leaf configurations will not be saved."
        DEFVAL        { false }
        ::= { rc2kBootConfigEntry 54 }

rc2kBootConfigEnableVrfScaling  OBJECT-TYPE
        SYNTAX        TruthValue
        MAX-ACCESS    read-write
        STATUS        current
        DESCRIPTION   "Flag to Enable or Disable vrf scaling."
        DEFVAL        { false }
        ::= { rc2kBootConfigEntry 55}

rc2kBootConfigLinerateDirectedBroadcast  OBJECT-TYPE
        SYNTAX        TruthValue
        MAX-ACCESS    read-write
        STATUS        current
        DESCRIPTION   "Flag to Enable or Disable Linerate Directed Broadcast.
	    	       With this flag set, IP directed broadcast will operate
		       at linerate. Without this flag, all IP directed broadcast
		       is handled in legacy mode by the CP and is limited to
		       a few hundred pps. When booted with the flag set, 
		       faceplate port 1/48 is removed from service and
		       recommissioned as a loopback port to which all directed
		       broadcast traffic is sent. The traffic can then reenter
		       the pipeline and flooded over the VLAN at linrate."
        DEFVAL        { false }
        ::= { rc2kBootConfigEntry 56 }

rc2kBootConfigVcMode  OBJECT-TYPE
        SYNTAX        TruthValue
        MAX-ACCESS    read-write
        STATUS        current
        DESCRIPTION   "Flag to Enable or Disable Virtual Chassis mode."
        DEFVAL        { false } 
        ::= { rc2kBootConfigEntry 57 }

rc2kBootConfigEnableIpv6EgressFilterMode OBJECT-TYPE
        SYNTAX        TruthValue
        MAX-ACCESS    read-write
        STATUS        current
        DESCRIPTION   "Flag to enable or disable the IPV6 egress filter"
        ::= { rc2kBootConfigEntry  58}

rc2kBootConfigEnableSyslogRfc5424Format  OBJECT-TYPE
        SYNTAX        TruthValue
        MAX-ACCESS    read-write
        STATUS        current
        DESCRIPTION   "Flag to enable or disable the syslog output format.
                       Enable will align syslog format with RFC 5424."
        DEFVAL        { true } 
        ::= { rc2kBootConfigEntry 59}
    
rc2kBootConfigEnableFactoryDefaultsMode OBJECT-TYPE
        SYNTAX       INTEGER {
                         false(1),
                         fabric(2),
                         noFabric(3)  
                      }
        MAX-ACCESS    read-write
        STATUS        current
        DESCRIPTION   "Set Factory default boot wiht option. This object is used to
	               deprecate and obsolete the rc2kBootConfigEnableFactoryDefaults
		       disable(1):  System boot up with no default configuration.
		       fabric(2):   System boot up with default setting and set up the fabric 
		       noFabric(3): system boot up with default setting and no fabric. this 
		                   equavalent to (true) in obect rc2kBootConfigEnableFactoryDefaults"
        ::= { rc2kBootConfigEntry 60 }


    
-- 2k Card table

rc2kCardTable OBJECT-TYPE
        SYNTAX        SEQUENCE OF Rc2kCardEntry
        MAX-ACCESS    not-accessible
        STATUS        current
        DESCRIPTION   "2k Card table"
        ::= { rc2k 6 }

rc2kCardEntry OBJECT-TYPE
        SYNTAX        Rc2kCardEntry
        MAX-ACCESS    not-accessible
        STATUS        current
        DESCRIPTION   "Entry containing information of 2k Card"
        INDEX         { rc2kCardIndex }
        ::= { rc2kCardTable 1 }

Rc2kCardEntry ::= SEQUENCE {
                rc2kCardIndex            INTEGER,
                rc2kCardFrontType        INTEGER,
                rc2kCardFrontDescription DisplayString,
                rc2kCardFrontAdminStatus INTEGER,
                rc2kCardFrontOperStatus  INTEGER,
                rc2kCardFrontSerialNum   DisplayString,
                rc2kCardFrontHwVersion   DisplayString,
                rc2kCardFrontPartNumber  DisplayString,
                rc2kCardFrontDateCode    DisplayString,
                rc2kCardFrontDeviations  DisplayString,
                rc2kCardFrontMacAddr     MacAddress,    --excluded
                rc2kCardBackType         INTEGER,
                rc2kCardBackDescription  DisplayString,
                rc2kCardBackSerialNum    DisplayString,
                rc2kCardBackHwVersion    DisplayString,
                rc2kCardBackPartNumber   DisplayString,
                rc2kCardBackDateCode     DisplayString,
                rc2kCardBackDeviations   DisplayString,
		rc2kCardPCMCIAType	 INTEGER,
		rc2kCardPCMCIADescr	 DisplayString,
		rc2kCardASICDescr	 DisplayString,
		rc2kCardFrontMasterIO	 TruthValue,
                rc2kCardSmltOnSingleCpSupported   TruthValue,
                rc2kCardMezzCard         INTEGER,
                rc2kCardFrontPoeOperStatus   INTEGER,
                rc2kCardMezzSerialNum        OCTET STRING,
                rc2kCardMezzHwVersion        INTEGER,
                rc2kCardMezzPartNum          INTEGER,
                rc2kCardSlotPriority         INTEGER,
		rc2kCardSlotOriginalPriority INTEGER,
		rc2kCardMode             INTEGER,
		rc2kCardSlotPower        INTEGER,
		rc2kCardModuleSerialNum    DisplayString,
                rc2kCardModulePartNumber   DisplayString,
                rc2kCardModuleAssemblyDate DisplayString
        }

rc2kCardIndex OBJECT-TYPE
        SYNTAX        INTEGER (1..32)
        MAX-ACCESS    read-only
        STATUS        current
        DESCRIPTION   "slot number."
        ::= { rc2kCardEntry 1 }

rc2kCardFrontType OBJECT-TYPE
        SYNTAX        INTEGER
                      {
        other(1),                        -- no card installed
        rc2kCPU(537788672),              -- 0010 0000 0000 1110 0000 0001 0000 0000
        rc2k48x100BaseTX(539033904),     -- 0010 0000 0010 0001 0000 0001 0011 0000
        rc2k24x100BaseTX(539033880),     -- 0010 0000 0010 0001 0000 0001 0001 1000
        rc2k32x100BaseTX(539033888),     -- 0010 0000 0010 0001 0000 0001 0010 0000
        rc2k8x1000BaseT(539099400),      -- 0010 0000 0010 0010 0000 0001 0000 1000  
        rc2k16x1000BaseT(539099408),     -- 0010 0000 0010 0010 0000 0001 0001 0000  
        rc2k24x100BaseFX(540082456),     -- 0010 0000 0011 0001 0000 0001 0001 1000
        rc2k8x1000BaseSXBB(540147976),   -- 0010 0000 0011 0010 0000 0001 0000 1000
        rc2k16x1000BaseSXBB(540147984),  -- 0010 0000 0011 0010 0000 0001 0001 0000 
        rc2k8x1000BaseLXBB(540156168),   -- 0010 0000 0011 0010 0010 0001 0000 1000
        rc2k8x1000BaseXDBB(540164360),   -- 0010 0000 0011 0010 0100 0001 0000 1000
        rc2k4x1000BaseOPM(540168452),    -- 0010 0000 0011 0010 0101 0001 0000 0100    
        rc2k8x1000BaseIC(540168456),     -- 0010 0000 0011 0010 0101 0001 0000 1000 
        rc2k16x1000BaseIC(540168464),    -- 0010 0000 0011 0010 0101 0001 0001 0000
        rc2k8x1000BaseSXRBB(540180744),  -- 0010 0000 0011 0010 1000 0001 0000 1000
        rc2k8x1000BaseLXRBB(540188936),  -- 0010 0000 0011 0010 1010 0001 0000 1000
        rc2k8xOC3(541327624),            -- 0010 0000 0100 0100 0000 0001 0000 1000
        rc2k2xOC12(541393154),           -- 0010 0000 0100 0101 0000 0001 0000 0010
        rc2k6xPOS(541401350),            -- 0010 0000 0100 0101 0010 0001 0000 0110
        rc2k4xATM(542441732),            -- 0010 0000 0101 0101 0000 0001 0000 0100
        rc2k8xATM(542441736),            -- 0010 0000 0101 0101 0000 0001 0000 1000
        rc2kRMON(545128704),             -- 0010 0000 0111 1110 0000 0001 0000 0000
        rc2k1x10GBaseLW(573767937),      -- 0010 0000 0011 0011 0000 0001 0000 0001
        rc2k1x10GBaseLR(573784321),      -- 0010 0000 0011 0011 0100 0001 0000 0001
        rc2k32x100BaseTXM(572588320),    -- 0010 0010 0010 0001 0000 0001 0010 0000
        rc2k48x100BaseTXM(572588336),    -- 0010 0010 0010 0001 0000 0001 0011 0000
        rc2k8x1000BaseTM(572653832),     -- 0010 0010 0010 0010 0000 0001 0000 1000
        rc2k8x1000BaseSXBBM(573702408),  -- 0010 0010 0011 0010 0000 0001 0000 1000
        rc2k8x1000BaseICM(573722888),    -- 0010 0010 0011 0010 0101 0001 0000 1000
        rc2k6xPOSM(574955782),           -- 0010 0010 0100 0101 0010 0001 0000 0110
        rc2k8xATMM(575996168),           -- 0010 0010 0101 0101 0000 0001 0000 1000
        -- ERS8600 PR card types       
        rc2kPR48X1000BaseTX(606208304),  -- 0010 0100 0010 0010 0000 0001 0011 0000
        rc2kPR30X1000BaseSXBB(607277342),-- 0010 0100 0011 0010 0101 0001 0001 1110
        rc2kPR3X10GBaseGbic(607338755),  -- 0010 0100 0011 0011 0100 0001 0000 0011 
        rc2kPR3X10GBaseXZW(607346947),   -- 0010 0100 0011 0011 0110 0001 0000 0011 
        rc2kPR48x1000BaseGBRS(607277360),        -- 0010 0100 0011 0010 0101 0001 0011 0000 0x24325130
        rc2kPR48x1000BaseGTRS(606241072),        -- 0010 0100 0010 0010 1000 0001 0011 0000 0x24228130
        rc2kPR12X10GBaseXLRS(607338764),         -- 0010 0100 0011 0011 0100 0001 0000 1100 0x2433410C
        rc2kPR34xXGRS(607277346),       -- 0010 0100 0011 0010 0101 0001 0010 0010 0x24325122
        -- OE RC-Module Front types
        rc2kPR48x1000BaseGXRS(607310128),-- 0010 0100 0011 0010 1101 0001 0011 0000 0x2432D130
        rc2kPR30x1000BaseGBRS(607310110),-- 0010 0100 0011 0010 1101 0001 0001 1110 0x2432D11E
	rc2kPR6X10GBaseXLRS(607338758),  -- 0010 0100 0011 0011 0100 0001 0000 0110 0x24334106
	rc2kPR26xXGRS(607277338),         -- 0010 0100 0011 0010 0101 0001 0001 1010 0x2432511A 
        rc2kMg48x100BaseTX(807469360),   -- 0011 0000 0010 0001 0000 0001 0011 0000
        rc2kMg32x100BaseTX(807473440),   -- 0011 0000 0010 0001 0001 0001 0010 0000
        rc2kMg16x100BaseFX(808522000),   -- 0011 0000 0011 0001 0001 0001 0001 0000
        rc2kMg8x1000BaseTX(808583432),   -- 0011 0000 0011 0010 0000 0001 0000 1000
        rc2kMg8x1000BaseIC(808603912),   -- 0011 0000 0011 0010 0101 0001 0000 1000
        rc2kMg48x100BaseTC(817955120),   -- 0011 0000 1100 0001 0000 0001 0011 0000,
        -- 8895 CP (RED == REDesign)
	rc2kCPURed(537792768),   	-- 0010 0000 0000 1110 0001 0001 0000 0000 0x200E1100
        -- Cobra card types --
        rc2kCobra48x100BaseT(1073807408), -- 0100 0000 0000 0001 0000 0000 0011 0000
        rc2kCobra24x1000BaseG(1073872920), -- 0100 0000 0000 0010 0000 0000 0001 1000
        rc2kCobra12x1000BaseG(1073872908), -- 0100 0000 0000 0010 0000 0000 0000 1100
-- ESM card type
        rc2k8x1000BaseOPM(1077039368),     -- 0100 0000 0011 0010 0101 0001 0000 1000
-- Cobalt Blue: if you change here, you MUST update rcCardType in rcCardTable
        cbMidplane-28(1090388736),         -- 0100 0000 1111 1110 0000 0011 0000 0000 0x40FE0300
	cbMidplaneSapphire(1090388737),    -- 0100 0000 1111 1110 0000 0011 0000 0001 0x40FE0301
	cbACPowerSupply(1084097280),       -- 0100 0000 1001 1110 0000 0011 0000 0000 0x409E0300
        cbACPowerPlusSupply(1084130048),   -- 0100 0000 1001 1110 1000 0110 0000 0000 0x409E8300
        cbCPFanTray(1085145856),           -- 0100 0000 1010 1110 0000 0011 0000 0000 0x40AE0300
        cbIOFanTray(1085149952),           -- 0100 0000 1001 1110 0000 0011 0000 0000 0x40AE1300
	cbFanTray(1085154048),             -- 0100 0000 1010 1110 0010 0011 0000 0000 0x40AE2300
        cbHSFanTray(1085158144),           -- 0100 0000 1010 1110 0011 0011 0000 0000 0x40AE3300	
        cbAUX(1091437312),                 -- 0100 0001 0000 1110 0000 0011 0000 0000 0x410E0300
        cbSF3200(1075708672),              -- 0100 0000 0001 1110 0000 0011 0000 0000 0x401E0300
        cbSF9600(1075712768),              -- 0100 0000 0001 1110 0001 0011 0000 0000 0x401E1300
	cbSF9610(1075712769),               -- 0100 0000 0001 1110 0001 0011 0000 0001 0x401E1301	
	cbCP-CSC(1073873665),              -- 0100 0000 0000 0010 0000 0011 0000 0001 0x40020301
        cb48x1000BaseTX(1075970864),       -- 0100 0000 0010 0010 0000 0011 0011 0000 0x40220330
        cb48x1000BaseTXPOE(1075974960),    -- 0100 0000 0010 0010 0001 0011 0011 0000 0x40221330
        cb48x1000SFP(1077044016),          -- 0100 0000 0011 0010 0110 0011 0011 0000 0x40326330
        cb24x10GBaseSFP(1077109528),       -- 0100 0000 0011 0011 0110 0011 0001 1000 0x40336318
        cb48x10GBaseSFP(1077109552),       -- 0100 0000 0011 0011 0110 0011 0011 0000 0x40336330
-- Future CB Cards
--      cbOPM(1087243008)                     0x40CE0300
--      cbSAS(1087247104)                     0x40CE1300
--      cbIPFIX(1087251200)                   0x40CE2300
-- CB generation 2 (ROF) linecards
	rof48x1000SFP(1144152880),         	 -- 0100 0100 0011 0010 0110 0011 0011 0000 0x44326330
 	rofLoadBoard(1144152832),          	 -- 0100 0100 0011 0010 0110 0011 0000 0000 0x44326300
 	rof16x10GBaseSFP(1144218384),      	 -- 0100 0100 0011 0011 0110 0011 0001 0000 0x44336310
 	rof48x10GBaseSFP(1144218416),      	 -- 0100 0100 0011 0011 0110 0011 0011 0000 0x44336330
 	rof4x40GBaseSFP(1144283920),       	 -- 0100 0100 0011 0100 0110 0011 0001 0000 0x44346310
 	rof12x40GBaseSFP(1144283952),      	 -- 0100 0100 0011 0100 0110 0011 0011 0000 0x44346330
        -- PP8300 card types
        rc2kPP8300-CPU8x1000BaseSFP(1342316808), -- 0101 0000 0000 0010 0010 0001 0000 1000 0x50022108
        rc2kPP8300-CPU8x1000BaseSFP256(1360142600), -- 0101 0001 0001 0010 0010 0001 0000 1000 0x51122108
        rc2kPP8300-24x1000BaseTX(1344405784),    -- 0101 0000 0010 0010 0000 0001 0001 1000 0x50220118
        rc2kPP8300-48x100BaseTX(1344340272),     -- 0101 0000 0010 0001 0000 0001 0011 0000 0x50210130
        rc2kPP8300-48x100BaseTXPOE(1344344368),   -- 0101 0000 0010 0001 0001 0001 0011 0000 0x50211130
        rc2kPP8300-24x100BaseFX(1345388824),     -- 0101 0000 0011 0001 0000 0001 0001 1000 0x50310118
        rc2kPP8300-48x1000BaseTX-4B(1344422192),    -- 0101 0000 0010 0010 0100 0001 0011 0000 0x50224130
        rc2kPP8300-48x1000BaseTXPOE-4B(1344426288), -- 0101 0000 0010 0010 0101 0001 0011 0000 0x50225130
        rc2kPP8300-48x1000BaseSFP-2B(1345454384),    -- 0101 0000 0011 0010 0000 0001 0011 0000 0x50320130
        rc2kPP8300-CPU2x10GBaseXFP(1342390530),     -- 0101 0000 0000 0011 0100 0001 0000 0010 0x50034102
        rc2kPP8300-8x10GBaseXFP-4B(1345519880),     -- 0101 0000 0011 0011 0000 0001 0000 1000 0x50330108
        rc2k61AlteonSAM(1926365441),     -- 0111 0010 1101 0010 0000 0001 0000 0001
        rc2k62AlteonSAM(1926369537),     -- 0111 0010 1101 0010 0001 0001 0000 0001
        rc2kAlteonLP(1893859592),        -- 0111 0000 1110 0010 0000 0001 0000 1000
        rc2kAlteonWSM(1899102468),       -- 0111 0001 0011 0010 0000 0001 0000 0100
        rc2kAlteonASFM(1899106564),      -- 0111 0001 0011 0010 0001 0001 0000 0100
-- Thunderbolt card types definition have been removed due to project cancellation
	--      88xx IO modules
	rc2kPRE48x1000BaseGB(632443184),        -- 0010 0101 1011 0010 0101 0001 0011 0000 0x25B25130
	rc2kPRE48x1000BaseGT(631406896),        -- 0010 0101 1010 0010 1000 0001 0011 0000 0x25A28130
	rc2kPRE12X10GBaseXL(632504588),         -- 0010 0101 1011 0011 0100 0001 0000 1100 0x25B3410C
	rc2kPRE12X10GBaseXLJ(632512780),        -- 0010 0101 1011 0011 0110 0001 0000 1100 0x25B3610C
	rc2kPRE34xXG(632443170),                 -- 0010 0101 1011 0010 0101 0001 0010 0010 0x25B25122
	-- 12X10GBaseXLRSJ (8612XLRSJ) Card for the ERS 8600 Federal stream
        rc2kPR12X10GBaseXLRSJ(607346956),       -- 0010 0100 0011 0011 0110 0001 0000 1100 0x2433610C
-- VSP4K card definitions
	vsp4k4850GTS(1232273458),                -- 0100 1001 0111 0011 0000 0000 0011 0010 0x49730032
	vsp4k4850GTSPWRPLUS(1232277554),          -- 0100 1001 0111 0011 0001 0000 0011 0010 0x49731032
        vsp4k4450GSXPWRPLUS(1231228978),          -- 0100 1001 0110 0011 0001 0000 0011 0010 0x49631032
	vsp4k4450GSX(1231224882),               -- 0100 1001 0110 0011 0000 0000 0011 0010 0x49630032	
	vsp4k4450GTXHTPWRPLUS(1232279602),        -- 0100 1001 0111 0011 0001 1000 0011 0010 0x49731832
-- VSP8200		
	vsp8k8242XSQ(1298407466),                 -- 0100 1101 0110 0100 0010 0000 0010 1010 0x4d64202a
-- VSP8400
	vsp8k8404(1331823105),         -- 0100 1111 0110 0010 0000 0010 0000 0001 0x4f620201
        vsp8k8404C(1331839489),        -- 0100 1111 0110 0010 0100 0010 0000 0001 0x4f624201 
	vsp8k8424XS(1298379288),       -- 0100 1101 0110 0011 1011 0010 0001 1000 0x4d63b218 (24x1/10G Fiber) 
	vsp8k8424XT(1293136408),       -- 0100 1101 0001 0011 1011 0010 0001 1000 0x4d13b218  (24x1/10G Copper) 
        vsp8k8408QQ(1298432544),       -- 0100 1101 0110 0100 1000 0010 0010 0000 0x4d648220 (8x40G QSFP+)    
	vsp8k8418XSQ(1298461208),      -- 0100 1101 0110 0100 1111 0010 0001 1000 0x4d64f218 (16x1/10G SFP & 2x40G QSFP+)
	vsp8k8418XTQ(1299509784),      -- 0100 1101 0111 0100 1111 0010 0001 1000 0x4d74f218 (16x1/10G COPPER & 2x40G QSFP+)
	vsp8k8402CQ(1298498050),       -- 0100 1101 0110 0101 1000 0010 0000 0010 0x4d658202 (2x100G QSPF28)
	vsp8k8424GS(1298326040),       -- 0100 1101 0110 0010 1110 0010 0001 1000 0x4d62e218 (24x100/1000 SFP)
	vsp8k8424GT(1294107160),       -- 0100 1101 0010 0010 1000 0010 0001 1000 0x4d228218 (24x10/100/1000 Copper)
-- NetApp
        netApp8016QQ(895778868),      -- 0011 0101 0110 0100 1000 0000 0011 0100  (0x35648034) (16x40G QSFP+)
-- Tsunami
        vsp8608(1458700545),          -- 0101 0110 1111 0010 0000 0001 0000 0001  (0x56f20101) (CP)
	vsp8624XS(1446215960),        -- 0101 0110 0011 0011 1000 0001 0001 1000  (0x56338118) (24x10G Fiber)
	vsp8624XT(1445167384),        -- 0101 0110 0010 0011 1000 0001 0001 1000  (0x56238118) (24x10G Copper)
	vsp8616QQ(1446281500),        -- 0101 0110 0011 0100 1000 0001 0001 1100  (0x5634811c) (16x40G QSFP+)
        vsp8606CQ(1446347032),        -- 0101 0110 0011 0101 1000 0001 0001 1000  (0x56358118) (6x100G XQSPF+)
	vsp8600SF(1411293440),        -- 0101 0100 0001 1110 1010 0001 0000 0000  (0x541EA100) (SF Card)
		
-- VSP7200	
	vsp7k7248XS(1298378800),      -- 0100 1101 0110 0011 1011 0000 0011 0000 0x4d63b030 (48x10G SFP+)
        vsp7k7206QQ(1298432024),      -- 0100 1101 0110 0100 1000 0000 0001 1000 0x4d648018 (6x40G channelized QSFP+)
        vsp7k7248XT(1294184496),       -- 0100 1101 0010 0011 1011 0000 0011 0000 0x4d23b030 (48x10G Copper)
-- APLS
        dsg6248GTS(1232274482),        -- 0100 1001 0111 0011 0000 0100 0011 0010  (0x49730432)
	dsg6248GTSPWRPLUS(1232278578), -- 0100 1001 0111 0011 0001 0100 0011 0010  (0x49731432)
	dsg8016QQ(895779892),          -- 0011 0101 0110 0100 1000 0100 0011 0100  (0x35648434) (16x40G QSFP+)
	dsg7006QQ(1298433048),         -- 0100 1101 0110 0100 1000 0100 0001 1000  (0x4d648418) (6x40G channelized QSFP+)
        dsg7048XS(1298379824),         -- 0100 1101 0110 0011 1011 0100 0011 0000  (0x4d63b430) (48x10G SFP+)	
	dsg7048XT(1294185520),         -- 0100 1101 0010 0011 1011 0100 0011 0000  (0x4d23b430) (48x10G Copper)	
        dsg7240XSQ(1298408490),        -- 0100 1101 0110 0100 0010 0100 0010 1010  (0x4d64242a) (40x10G + 2x40G) 
	dsg6248GSX(1231225906),         -- 0100 1001 0110 0011 0000 0100 0011 0010  (0x49630432) (48x1G + 2x10G)

-- ES7400
	vsp7432CQ(1332072512),        -- 0100 1111 0110 0101 1101 0000 0100 0000  (0x4f65d040) (32 x100G) Display: 7432CQ
	vsp7456VSC(1332138032),       -- 0100 1111 0110 0110 1101 0000 0011 0000  (0x4f66d030) (48 x 25G) Display: 7456VSC
	vsp7400x8C(1332073480),        -- 0100 1111 0110 0101 1101 0100 0000 1000  (0x4f65d408) (8x100G for intenal use)
	vsp10GInsight(1332073474),     -- 0100 1111 0110 0101 1101 0100 0000 0010  (0x4f65d402) (2x10G sideband for internal uses)

-- VSP4600
     vsp4624GTSPWRPLUS(2065862680),-- 0111 1011 0010 0010 1001 0000 0001 1000  (0x7B229018) (24 x 10/100/1000Mb Poe COPPER) Display:4624GTSPWRPLUS
     vsp4648GTSPWRPLUS(2065862704),-- 0111 1011 0010 0010 1001 0000 0011 0000  (2065862704) (48 x 10/100/1000Mb Poe COPPER) Display:4648GTSPWRPLUS
     vsp4600x4x(2036564484),       -- 0111 1001 0110 0011 1000 0010 0000 0100  (0x79638204) (4  x 10G Fiber) Display: 4600-4x
     vsp4600x4xLM(2036568580),     -- 0111 1001 0110 0011 1001 0010 0000 0100  (0x79639204) (4  x 10G Fiber with Macsec) Display: 4600-4xLM
     vsp4600x2q(2036630018),       -- 0111 1001 0110 0100 1000 0010 0000 0010  (0x79648202) (2  x 40G Fiber) Display: 4600-2q
     vsp4600x2v(2036761090),       -- 0111 1001 0110 0110 1000 0010 0000 0010  (0x79668202) (2  x 25G Fiber) Display: 4600-2v
     vsp4600x4vLM(2036765188)      -- 0111 1001 0110 0110 1001 0010 0000 0100  (0x79669204) (4  x 25G Fiber with Macsec) Display: 4600-2vLM
	
        }
        MAX-ACCESS    read-only
        STATUS        current
        DESCRIPTION     "Used to indicate card types in the Accelar
                        8000 product families.

			For Accelar 8000 devices, all cards use
		      	an encoded value according to the following rule:
                       
			Exampe: 
                             Titan VSP7400-(port configuration)
                             Seadart: VSP4600-12mu-12xLM-1VIM

			dash '-' cannot be used in the MIB defintion. Using 'x'
			to instead.

			Port and Port Type representation:

			  t for 10/100/1000
			  p for 10/100/1000 30W PoE
			  u for 10/100/1000 60W PoE
			  w for 10/100/1000 90W PoE
			  x for SFP/SFP+
			  m for multirate (2.5G/5G/10G)
			  v for 25Gbe
			  q for 40GbE
			  c for 100GbE
                          LM = Long Reach Multimode and MACsec (port has PHYs)
                          The -1VIM means the switch has a VIM slot 

        |   6  |   1   |   5   |   4   |  1 |   3   |  4   |      8      |
        +------+-------+-------+-------+------------+------+------+------+
bits  : |31-26 |    25 | 24-20 | 19-16 | 15 | 14-12 | 11-8 |     7-0     |
        +------+-------+-------+-------+----+-------+------+------+------+
field : |  a   |   b   |   c   |   d   |  e |    f  |  g   |      h      |
        +------+-------+-------+-------+----+-------+------+------+------+

     a : Family type/Product line (6 bits (5 bits usuable) (was 4 bits))
            MSB bit31 should not be used (MIB compiler fails)
	    0x0-00 = 0000-00 = Reserved
            0x1-00 = 0001-00 = Monoploy non specific (e.g backplane, psu, fans)
            0x2-00 = 0010-00 = Boardwalk
            0x2-01 = 0010-01 = Power Ranger
            0x3-00 = 0011-00 = Marvin Gardens
	    0x3-01 = 0011-01 = DSG8032
	    0x3-11 = 0011-11 = i86 Family (DSG9032, DSG8064)
            0x4-00 = 0100-00 = Cobalt Blue (was Thunderbolt and Pacific before that - both are obsolete)
	    0x4-01 = 0100-01 = Ring Of Fire
	    0x4-10 = 0100-10 = VSP4K
	    0x4-11 = 0100-11 = VSP8k, VSP7k, VSP7400	    
            0x5-00 = 0101-00 = PP8300 (was ParkPlace)
	    0x5-01 = 0101-01 = VSP9400
            0x6-00 = 0110-00 = Central Office (only used in chassis)
            0x7-00 = 0111-00 = Alteon WebSystems
            0x7-01 = 0111-01 = VSP5K IcePick
            0x7-02 = 0111-10 = VSP4600
	   
	    
     b : Interface / Device type variation: (Were 3 bits, 2 bits taken by family)
            0x1 = 0 = Non M-Module 
            0x1 = 1 = M-module (128K RARU records)
	    0x0 = 0 = VSP4k No Mgmt port
	    0x1 = 1 = VSP8K With Mgmt Port

     c : Interface / device type:
            0x0 = 00000 = CPU
            0x1 = 00001 = Switch fabric
            0x2 = 00010 = Copper Ethernet
            0x3 = 00011 = Fiber Ethernet
            0x4 = 00100 = Sonet (Packets)
            0x5 = 00101 = ATM
            0x6 = 00110 = Token Ring
            0x7 = 00111 = RMON
            0x8 = 01000 = BFM (Frame or cells indicated by field 'a' above)
            0x9 = 01001 = PSU
            0xa = 01010 = Fan Tray
            0xb = 01011 = Chassis/Backplane
            0xc = 01100 = CPU Mezz
            0xd = 01101 = SSL
            0xe = 01110 = Launch Pad
            0xf = 01111 = Chassis/Midplane
            0x10 = 10000 = Auxillary Card
            0x11 = 10001 = CPU w/256M SDRAM
            0x12 = 10010 = Single Card Switch (Copper Type)
            0x13 = 10011 = WSM Fiber Ethernet
	    0x14 = 
	    0x16 = 10110 = Single Card Switch (Fiber Type)
            0x17 = 10111 = Single Card Switch (Combo port type)
	    
     d : Maximum speed (highest negotiable speed)
            0x0 = 0000 = 10 Mbit  
            0x1 = 0001 = 100 Mbit  
            0x2 = 0010 = 1 Gbit
            0x3 = 0011 = 10 Gbit
            0x4 = 0100 = OC-3
	    0x4 = 0100 = 40 Gbit for VSP 
            0x5 = 0101 = OC-12
            0x5 = 0101 = 100 Gbit for VSP
            0x6 = 0110 = OC-48
            0x7 = 0111 = OC-92
            0x8 = 1000 = OC-192
            0x9 = 1001 = 4 Mbit (TR)
            0xa = 1010 = 16 Mbit (TR)
            0xb = 1011 = E3 
            0xc = 1100 = DS1
            0xd = 1101 = DS3
            0xe = 1110 = none (no PHY interfaces on board)
            0xf = 1111 = Max speed indicated implicitly in field (c) (for expansion)
  
     e : 0=non-redundant,  (1 bit)
         1=redundant
	 For Line card or MDA
	   0 = prototype 1 = Product

     f : Card specific info. (3 bits)
             For Gigabit used as follows:
		 000=short-haul (SX)
		 010=long-haul (LX)
		 100=extra-distance (DX)
                 101=GBIC
	     For 10 Gigabit used as follws
	         000 = 10GE WAN serial 1310nm (XLW)
		 001 = 10GE WAN serial 1550nm (XEW)
		 100 = 10GE LAN serial 1310nm (XLR)
		 101 = 10GE LAN serial 1550nm (XER)
		 110 = 10GE LAN serial 1310nm (XLRSJ)
	     For ATM/Sonet used as follows
                 000 = multi mode
                 001 = single mode
                 010 = single or multimode
		 011 = not applicable (e.g., copper has no mode)
             For Marvin Gardens, indicates number of MDA slots
                 000 = none
                 001 = one option slots
                 010 = two option slots
                 011 = three option slots
            For Power Supplies:
                 000 = AC PSU
                 001 = DC PSU
                 010 = PoE 1770W AC PSU
                 011 = PoE 1400W AC PSU
            For SSL:
                 000 = server offloading
                 001 = end to end encryption
            For WSM:
                 000 = WSM mode
                 001 = ASFM mode

	    For 8003 (3 slot) chassis differentiation:
                 000 = ERS 8003
                 001 = MERS 8003-R (Triumph)

            For PP8300 I/O or CP:
                 000: PP8300 48TX, 10/100/1000 without POL
                 001: PP8300 48TX, 10/100/1000 with POL
                 010: SFP
                 000: non SFP
            For Cobra Chassis:
                 001: 12G
                 010: 24G
                 100: 48T
            For SF:
		 000 = 3200 card
		 001 = 9600 card
		 010 = 9400 card
             For Copper Ethernet:
		 000: no POE
		 001: POE
	     For FAN Tray:
		 000: CP
		 001: IO	
	     For Objects with no options:
		 000: CPU, Mezz, OPM, SAS, IPFIX		 
	     For VSP4K/6K/9400:
	         000: no POE 
	         001: POE
		 010: SFP+
		 011: COPPER
	     For Chassis :
	         000: Non-Trident2+
		 100: Trident2 +
		 
     g : Chassis type (4 bits, possibly MSB 2 bits are extension of field b)
         Using the upper bit to indicate the High temperature of the chassis type
         0x0 = 0000 = work-group (single card switches, etc)
         0x1 = 0001 = back-bone (chassis based products)
         0x2 = 0010 = MDA (option modules)
	 0x3 = 00-11 = mid-plane (chassis based products)
         0x8 = 1000 = High Temperature single card switches
	 0x4 = x1xx = equal to APLS device
	 
     h : Number of ports (binary representation obmited)
         (for ACIM/BFM cards, this is number of octapids/blackbirds/dea)
               0x00 =  no ports (cpus, switch fabrics)
               0x01 =  1-port, 
               0x02 =  2-port, 
               0x04 =  4-port,
               0x06 =  6-port,
               0x08 =  8-port,
               0x0c = 12-port,
               0x10 = 16-port,
               0x18 = 24-port,
               0x22 = 36-port,
               0x30 = 48-port,
               0x40 = 64-port.

		"
        ::= { rc2kCardEntry 2 }

rc2kCardFrontDescription OBJECT-TYPE
        SYNTAX        DisplayString (SIZE (0..20))
        MAX-ACCESS    read-only
        STATUS        current
        DESCRIPTION   "description"
        ::= { rc2kCardEntry 3 }

rc2kCardFrontAdminStatus OBJECT-TYPE
        SYNTAX       INTEGER {
                         up(1),
                         down(2),
                         testing(3),
			 reset(4)
                      }
        MAX-ACCESS    read-write
        STATUS        current
        DESCRIPTION   "Used to indicate the administrative status of this
                       card"
        ::= { rc2kCardEntry 4 }

rc2kCardFrontOperStatus OBJECT-TYPE
        SYNTAX        INTEGER {
                         up(1),
                         down(2),
                         testing(3),
                         unknown(4),
                         dormant(5),
			 upMaster(6),
			 upDormant(7),
			 upWarmStandby(8)
                      }
        MAX-ACCESS    read-only
        STATUS        current
        DESCRIPTION   "Used to indicate the operational status of this card."
        ::= { rc2kCardEntry 5 }

rc2kCardFrontSerialNum OBJECT-TYPE
        SYNTAX        DisplayString (SIZE (0..20))
        MAX-ACCESS    read-only
        STATUS        current
        DESCRIPTION   "serial number of card"
        ::= { rc2kCardEntry 6 }

rc2kCardFrontHwVersion OBJECT-TYPE
        SYNTAX        DisplayString (SIZE (0..20))
        MAX-ACCESS    read-only
        STATUS        current
        DESCRIPTION   "hardware version"
        ::= { rc2kCardEntry 7 }

rc2kCardFrontPartNumber OBJECT-TYPE
        SYNTAX        DisplayString (SIZE (0..20))
        MAX-ACCESS    read-only
        STATUS        current
        DESCRIPTION   "part number"
        ::= { rc2kCardEntry 8 }

rc2kCardFrontDateCode OBJECT-TYPE
        SYNTAX        DisplayString (SIZE (0..20))
        MAX-ACCESS    read-only
        STATUS        current
        DESCRIPTION   "date code"
        ::= { rc2kCardEntry 9 }

rc2kCardFrontDeviations OBJECT-TYPE
        SYNTAX        DisplayString (SIZE (0..20))
        MAX-ACCESS    read-only
        STATUS        current
        DESCRIPTION   "deviations"
        ::= { rc2kCardEntry 10 }

rc2kCardFrontMacAddr OBJECT-TYPE
        SYNTAX        MacAddress
        MAX-ACCESS    read-only
        STATUS        obsolete
        DESCRIPTION   "base mac address"
        ::= { rc2kCardEntry 11 }

rc2kCardBackType OBJECT-TYPE
        SYNTAX        INTEGER {
        other(1),                  -- no card installed
        rc2kBackplane(536969472),  -- 0010 0000 0000 0001 1000 0001 0000 0000
        rc2kSFM(538837248),        -- 0010 0000 0001 1111 0000 0001 0000 0000
        rc2kBFM0(546177280),       -- 0010 0000 1000 1111 0000 0001 0000 0000
        rc2kBFM2(546177282),       -- 0010 0000 1000 1111 0000 0001 0000 0010
        rc2kBFM3(546177283),       -- 0010 0000 1000 1111 0000 0001 0000 0011
        rc2kBFM4(1888354564),      -- 0111 0000 1000 1110 0000 0001 0000 0100
        rc2kBFM6(546177286),       -- 0010 0000 1000 1111 0000 0001 0000 0100
        rc2kBFM8(546177288),       -- 0010 0000 1000 1111 0000 0001 0000 1000
        rc2kMGSFM(807272704),      -- 0011 0000 0001 1110 0000 0001 0000 0000
        rc2kFSFM(605946112),       -- 0010 0100 0001 1110 0000 0001 0000 0000
        rc2kDPM2(613351682),       -- 0010 0100 1000 1111 0000 0001 0000 0010
        rc2kDPM1(613351861),       -- 0010 0100 1000 1111 0000 0001 1011 0101
        rc2kDPM3(613351863),       -- 0010 0100 1000 1111 0000 0001 1011 0111
	rc2kEDPM2(613351690),      -- 0010 0100 1000 1111 0000 0001 0000 1010 0x248F010A
        rc2kEDPM3(613351871),      -- 0010 0100 1000 1111 0000 0001 1011 1111 0x248F01BF
    -- EDPM w/RSP2.7
	rc2kEEDPM2(630128906),      -- 0010 0101 1000 1111 0000 0001 0000 1010 0x258F010A
	rc2kEEDPM3(630129087)       -- 0010 0101 1000 1111 0000 0001 1011 1111 0x258F01BF
			}
        MAX-ACCESS    read-only
        STATUS        current
        DESCRIPTION   "Refer to rc2kCardFrontType for the encoding scheme"
        ::= { rc2kCardEntry 12 }

rc2kCardBackDescription OBJECT-TYPE
        SYNTAX        DisplayString (SIZE (0..20))
        MAX-ACCESS    read-only
        STATUS        current
        DESCRIPTION   "description"
        ::= { rc2kCardEntry 13 }

rc2kCardBackSerialNum OBJECT-TYPE
        SYNTAX        DisplayString (SIZE (0..20))
        MAX-ACCESS    read-only
        STATUS        current
        DESCRIPTION   "serial number of card"
        ::= { rc2kCardEntry 14 }

rc2kCardBackHwVersion OBJECT-TYPE
        SYNTAX        DisplayString (SIZE (0..20))
        MAX-ACCESS    read-only
        STATUS        current
        DESCRIPTION   "hardware version"
        ::= { rc2kCardEntry 15 }

rc2kCardBackPartNumber OBJECT-TYPE
        SYNTAX        DisplayString (SIZE (0..20))
        MAX-ACCESS    read-only
        STATUS        current
        DESCRIPTION   "part number"
        ::= { rc2kCardEntry 16 }

rc2kCardBackDateCode OBJECT-TYPE
        SYNTAX        DisplayString (SIZE (0..20))
        MAX-ACCESS    read-only
        STATUS        current
        DESCRIPTION   "date code"
        ::= { rc2kCardEntry 17 }

rc2kCardBackDeviations OBJECT-TYPE
        SYNTAX        DisplayString (SIZE (0..20))
        MAX-ACCESS    read-only
        STATUS        current
        DESCRIPTION   "deviations"
        ::= { rc2kCardEntry 18 }

rc2kCardPCMCIAType OBJECT-TYPE
        SYNTAX        INTEGER {
                         none(1),
			 modemCard(2),
                         ethernetCard(3),
                         ataDisk(4)
                      }  
        MAX-ACCESS    read-only
        STATUS        current
        DESCRIPTION   "Used to indicate the type of PCMCIA card currently
                      installed in this CPU card, if any.

                      For non-CPU cards, this variable has no meaning and
                      will always be set to none(1)."
        DEFVAL        { none }
        ::= { rc2kCardEntry 19 }

rc2kCardPCMCIADescr OBJECT-TYPE
        SYNTAX        DisplayString (SIZE (0..128))
        MAX-ACCESS    read-only
        STATUS        current
        DESCRIPTION   "PCMCIA descriptor"
        ::= { rc2kCardEntry 20 }

rc2kCardASICDescr OBJECT-TYPE
        SYNTAX        	DisplayString (SIZE (0..128))
        MAX-ACCESS        	read-only
        STATUS        	current
        DESCRIPTION   	"ASIC descriptor"
        ::= { rc2kCardEntry 21 }

rc2kCardFrontMasterIO OBJECT-TYPE
        SYNTAX        	TruthValue
        MAX-ACCESS        	read-only
        STATUS        	current
        DESCRIPTION   	"Used to indicate whether an IO card in a 8100 device
		       	is operating in the 'master' mode.

			This variable is not meaningful for non-IO cards and
			non-8100 devices."
	DEFVAL	      { false }
        ::= { rc2kCardEntry 22 }

rc2kCardSmltOnSingleCpSupported OBJECT-TYPE
        SYNTAX          TruthValue
        MAX-ACCESS      read-only
        STATUS          current
        DESCRIPTION     "Used to indicate whether an IO card is updated to
                         support SMLT on single Cp feature or not."
        DEFVAL        { false }
        ::= { rc2kCardEntry 23 }

rc2kCardMezzCard OBJECT-TYPE
        SYNTAX          INTEGER {
                        unsupported(1),
                        notpresent(2),
                        present(3),
                        running(4)
                        }
        MAX-ACCESS      read-only
        STATUS          current
        DESCRIPTION     "Used to indicate the CPU Mezz card"
        ::= { rc2kCardEntry 24 }

rc2kCardFrontPoeOperStatus OBJECT-TYPE
        SYNTAX        INTEGER {
                         up(1),
                         down(2),
                         testing(3),
                         unknown(4),
                         dormant(5),
                         failure(6)
                      }
        MAX-ACCESS    read-only
        STATUS        current
        DESCRIPTION   "Used to indicate the operational status of this card."
        ::= { rc2kCardEntry 25 }

rc2kCardMezzSerialNum OBJECT-TYPE 
           SYNTAX        OCTET STRING (SIZE(0..20))
           MAX-ACCESS    read-only
           STATUS        current
           DESCRIPTION   "Used to get the serial number of the mezz"
           ::= { rc2kCardEntry 26 }

rc2kCardMezzHwVersion OBJECT-TYPE
           SYNTAX        INTEGER {
                                  undefined(0),
                                  e0(1),
                                  e1(2),
                                  e2(3),
                                  e3(4),
                                  e4(5),
                                  e5(6),
                                  e6(7),
                                  e7(8)
                                 }
           MAX-ACCESS    read-only
           STATUS        current
           DESCRIPTION   "Used to get the HW version of the mezz. The
                          value of HW Version corresponds to the value of
                          part number."
           ::= { rc2kCardEntry 27 }

rc2kCardMezzPartNum OBJECT-TYPE
           SYNTAX        INTEGER {
                                  undefined(0),
                                  p120616(1),
                                  p120618(2),
                                  p120617(3),
                                  p120615(4),
                                  p120724(5),
                                  p120672(6),
                                  p120851(7),
                                  p120939(8)
                                 }
           MAX-ACCESS    read-only
           STATUS        current
           DESCRIPTION   "Used to get the part number of the mezz. The
                          value of part number corresponds to the value of
                          HW Version."
           ::= { rc2kCardEntry 28 }

rc2kCardSlotPriority OBJECT-TYPE
        SYNTAX       INTEGER
                     {
                       critical(1),
                       high(2),
                       low(3)
                     }
        MAX-ACCESS    read-write
        STATUS        current
        DESCRIPTION   "Used to indicate the priority of the slot for power
                       management.It will take effect only after reboot."
        ::= { rc2kCardEntry 29 }

rc2kCardSlotOriginalPriority OBJECT-TYPE
        SYNTAX       INTEGER
                     {
                       critical(1),
                       high(2),
                       low(3)
                     }
        MAX-ACCESS    read-only
        STATUS        current
        DESCRIPTION   "Priority of the slot for power management which the
                       swtich has currently booted with. It will remain the 
		       same until the next reboot."
        ::= { rc2kCardEntry 30 }

rc2kCardMode OBJECT-TYPE
        SYNTAX       INTEGER {
                         singleport(1),
                         dualport(2)
                      }
        MAX-ACCESS    read-write
        STATUS        current
        DESCRIPTION   "Used to indicate the single port or dual port is
                       using"
        ::= { rc2kCardEntry 31 }

rc2kCardSlotPower  OBJECT-TYPE
        SYNTAX       INTEGER
                     {
                       on(1),
                       off(2)
                     }
        MAX-ACCESS    read-write
        STATUS        current
        DESCRIPTION   "Administrately turn on or off power on this slot.
                       it only applicable on Standby CP & IO and SF Card"
        ::= { rc2kCardEntry 32 }
rc2kCardModuleSerialNum OBJECT-TYPE
        SYNTAX        DisplayString (SIZE (0..20))
        MAX-ACCESS    read-only
        STATUS        current
        DESCRIPTION   "Module serial number.
                       It is only applicable to the RS module. And it is not
                       applicable to old version of the R module and CP"
        ::= { rc2kCardEntry 33 }

rc2kCardModulePartNumber OBJECT-TYPE
        SYNTAX        DisplayString (SIZE (0..20))
        MAX-ACCESS    read-only
        STATUS        current
        DESCRIPTION   "Module part number.
   		       It is only applicable to the RS module. And it is not
                       applicable to old version of the R module and CP"           
        ::= { rc2kCardEntry 34 }

rc2kCardModuleAssemblyDate OBJECT-TYPE
        SYNTAX        DisplayString (SIZE (0..20))
        MAX-ACCESS    read-only
        STATUS        current
        DESCRIPTION   "Module assemly date.
                       It is only applicable to the RS module. And it is not
                       applicable to old version of the R module and CP"
        ::= { rc2kCardEntry 35 }

-- 2k copy file

rc2kCopyFile     OBJECT IDENTIFIER ::= { rc2k 7 }

rc2kCopyFileSource OBJECT-TYPE
        SYNTAX        OCTET STRING (SIZE(0..256))
        MAX-ACCESS    read-write
        STATUS        current
        DESCRIPTION   "source file"
        ::= { rc2kCopyFile 1 }

rc2kCopyFileDestination OBJECT-TYPE
        SYNTAX        OCTET STRING (SIZE(0..256))
        MAX-ACCESS    read-write
        STATUS        current
        DESCRIPTION   "dest file"
        ::= { rc2kCopyFile 2 }

rc2kCopyFileAction OBJECT-TYPE
        SYNTAX        INTEGER
                      {
                            none(1),
                            start(2)
                      }
        MAX-ACCESS    read-write
        STATUS        current
        DESCRIPTION   "start or cancell"
        ::= { rc2kCopyFile 3 }

rc2kCopyFileResult OBJECT-TYPE
        SYNTAX        INTEGER
                      {
                            none(1),
                            inProgress(2),
                            success(3),
                            fail(4),
                            invalidSource(5),
                            invalidDestination(6),
                            outOfMemory(7),
                            outOfSpace(8),
                            fileNotFound(9)
                      }
        MAX-ACCESS    read-only
        STATUS        current
        DESCRIPTION   "result"
        ::= { rc2kCopyFile 4 }

rc2kQos OBJECT IDENTIFIER ::= { rc2k 8 } -- defined in rc2kQosXXX.mib

rc2kAtm OBJECT IDENTIFIER ::= { rc2k 9 } -- defined in rc2kAtmXXX.mib

-- 2k Mda

rc2kMdaCardTable OBJECT-TYPE
        SYNTAX        SEQUENCE OF Rc2kMdaCardEntry
        MAX-ACCESS    not-accessible
        STATUS        current
        DESCRIPTION   "Mda card table"
        ::= { rc2k 10 }

rc2kMdaCardEntry OBJECT-TYPE
        SYNTAX        Rc2kMdaCardEntry
        MAX-ACCESS    not-accessible
        STATUS        current
        DESCRIPTION   "Entry containing infomation of Mda card"
        INDEX         { rc2kMdaCardSlotNum, rc2kMdaCardMdaNum }
        ::= { rc2kMdaCardTable 1 }

Rc2kMdaCardEntry ::= SEQUENCE {
                rc2kMdaCardSlotNum INTEGER,
                rc2kMdaCardMdaNum INTEGER,
                rc2kMdaCardType INTEGER,
                rc2kMdaCardDescription DisplayString,
                rc2kMdaCardAdminStatus INTEGER,
                rc2kMdaCardOperStatus INTEGER,
                rc2kMdaCardSerialNum DisplayString,
                rc2kMdaCardHwVersion DisplayString,
                rc2kMdaCardPartNumber DisplayString,
                rc2kMdaCardDateCode DisplayString,
                rc2kMdaCardDeviations DisplayString,
                rc2kMdaCardMacAddr MacAddress,
                rc2kMdaCardNumPorts Integer32,
                rc2kMdaCardFirstIfIndex InterfaceIndex,
                rc2kMdaCardLastIfIndex InterfaceIndex
        }

rc2kMdaCardSlotNum OBJECT-TYPE
        SYNTAX        INTEGER (1..10)
        MAX-ACCESS    read-only
        STATUS        current
        DESCRIPTION   "Slot number"
        ::= { rc2kMdaCardEntry 1 }

rc2kMdaCardMdaNum OBJECT-TYPE
        SYNTAX          INTEGER (1..4)
        MAX-ACCESS              read-only
        STATUS          current
        DESCRIPTION     "MDA number within slot.  MDAs are numbered
                        from left to right."
        ::= { rc2kMdaCardEntry 2 }

rc2kMdaCardType OBJECT-TYPE
        SYNTAX          INTEGER
                        {
        other(1),                        -- no card installed
        rc2k4x100BaseTX(807469572),      -- 0011 0000 0010 0001 0000 0010 0000 0100
        rc2k2x100BaseFX(808518146),      -- 0011 0000 0011 0001 0000 0010 0000 0010
        rc2k4x100BaseFX(808518148),      -- 0011 0000 0011 0001 0000 0010 0000 0100
        rc2k1x1000BaseSXBB(808583681),   -- 0011 0000 0011 0010 0000 0010 0000 0001
        rc2k1x1000BaseSXRBB(808616449),  -- 0011 0000 0011 0010 1000 0010 0000 0001
        rc2k1x1000BaseLXBB(808591873),   -- 0011 0000 0011 0010 0010 0010 0000 0001
        rc2k1x1000BaseLXRBB(808624641),  -- 0011 0000 0011 0010 1010 0010 0000 0001
        rc2k4xOc3cBaseSM(542380548),     -- 0010 0000 0101 0100 0001 0010 0000 0100
        rc2k4xOc3cBaseMM(542376452),     -- 0010 0000 0101 0100 0000 0010 0000 0100
        rc2k4xOc3cBaseCOPPER(542388740), -- 0010 0000 0101 0100 0011 0010 0000 0100
        rc2k1x0c12cBaseSM(542446081),    -- 0010 0000 0101 0101 0001 0010 0000 0001
        rc2k1x0c12cBaseMM(542441985),    -- 0010 0000 0101 0101 0000 0010 0000 0001
        rc2k2xDs3(542970370),            -- 0010 0000 0101 1101 0001 0010 0000 0010
        rc2k2xE3(542839298),             -- 0010 0000 0101 1011 0001 0010 0000 0010
        rc2k2xOc3PosBaseMMF(541327874),  -- 0010 0000 0100 0100 0000 0010 0000 0010
        rc2k2xOc3PosBaseSMF(541331970),  -- 0010 0000 0100 0100 0001 0010 0000 0010
        rc2k1xOc12PosBaseMMF(541393409), -- 0010 0000 0100 0101 0000 0010 0000 0001
        rc2k1xOc12PosBaseSMF(541397505)  -- 0010 0000 0100 0101 0001 0010 0000 0001

                        }
        MAX-ACCESS              read-only
        STATUS          current
        DESCRIPTION     "Refer to rc2kCardFrontType for the encoding scheme"
        ::= { rc2kMdaCardEntry 3 }

rc2kMdaCardDescription OBJECT-TYPE
        SYNTAX        DisplayString
        MAX-ACCESS    read-only
        STATUS        current
        DESCRIPTION   "description of mda card"
        ::= { rc2kMdaCardEntry 4 }

rc2kMdaCardAdminStatus OBJECT-TYPE
        SYNTAX        INTEGER {
                            up(0),
                            down(1),
                            testing(2),
                            unknown(3)
                      }
        MAX-ACCESS    read-write
        STATUS        current
        DESCRIPTION   "administration status of mda card"
        ::= { rc2kMdaCardEntry 5 }

rc2kMdaCardOperStatus OBJECT-TYPE
        SYNTAX        INTEGER {
                            up(0),
                            down(1),
                            testing(2),
                            unknown(3)
                      }
        MAX-ACCESS    read-only
        STATUS        current
        DESCRIPTION   "operation status of mda card."
        ::= { rc2kMdaCardEntry 6 }

rc2kMdaCardSerialNum OBJECT-TYPE
        SYNTAX        DisplayString
        MAX-ACCESS    read-only
        STATUS        current
        DESCRIPTION   "serial number of mad card"
        ::= { rc2kMdaCardEntry 7 }

rc2kMdaCardHwVersion OBJECT-TYPE
        SYNTAX        DisplayString
        MAX-ACCESS    read-only
        STATUS        current
        DESCRIPTION   "hardware version of mda card"
        ::= { rc2kMdaCardEntry 8 }

rc2kMdaCardPartNumber OBJECT-TYPE
        SYNTAX        DisplayString
        MAX-ACCESS    read-only
        STATUS        current
        DESCRIPTION   "part number of mda card"
        ::= { rc2kMdaCardEntry 9 }

rc2kMdaCardDateCode OBJECT-TYPE
        SYNTAX        DisplayString
        MAX-ACCESS    read-only
        STATUS        current
        DESCRIPTION   "date code of mda card"
        ::= { rc2kMdaCardEntry 10 }

rc2kMdaCardDeviations OBJECT-TYPE
        SYNTAX        DisplayString
        MAX-ACCESS    read-only
        STATUS        current
        DESCRIPTION   "hardware deviation infomation of mda card"
        ::= { rc2kMdaCardEntry 11 }

rc2kMdaCardMacAddr OBJECT-TYPE
        SYNTAX        MacAddress
        MAX-ACCESS    read-only
        STATUS        current
        DESCRIPTION   "base mac address of mda card"
        ::= { rc2kMdaCardEntry 12 }

rc2kMdaCardNumPorts OBJECT-TYPE
        SYNTAX        Integer32
        MAX-ACCESS    read-only
        STATUS        current
        DESCRIPTION   "number of ports on mda card"
        ::= { rc2kMdaCardEntry 13 }

rc2kMdaCardFirstIfIndex OBJECT-TYPE
        SYNTAX        InterfaceIndex
        MAX-ACCESS    read-only
        STATUS        current
        DESCRIPTION   "first ifindex number on mda card"
        ::= { rc2kMdaCardEntry 14 }

rc2kMdaCardLastIfIndex OBJECT-TYPE
        SYNTAX        InterfaceIndex
        MAX-ACCESS    read-only
        STATUS        current
        DESCRIPTION   "last ifindex number on mda card"
        ::= { rc2kMdaCardEntry 15 }

-- 2k CPU Ethernet Port Route table

rc2kCpuEthernetPortRouteTable OBJECT-TYPE
        SYNTAX        SEQUENCE OF Rc2kCpuEthernetPortRouteEntry
        MAX-ACCESS    not-accessible
        STATUS        current
        DESCRIPTION   "2k CPU Ethernet Port Route table"
        ::= { rc2k 11 }

rc2kCpuEthernetPortRouteEntry OBJECT-TYPE
        SYNTAX        Rc2kCpuEthernetPortRouteEntry
        MAX-ACCESS    not-accessible
        STATUS        current
        DESCRIPTION   "Entry containing infomation of 2k CPU Ethernet Port"
        INDEX         { rc2kCpuEthernetPortRouteNetwork, rc2kCpuEthernetPortRouteGateway}
        ::= { rc2kCpuEthernetPortRouteTable 1 }

Rc2kCpuEthernetPortRouteEntry ::= SEQUENCE {
                rc2kCpuEthernetPortRouteNetwork       IpAddress,
                rc2kCpuEthernetPortRouteGateway       IpAddress,
                rc2kCpuEthernetPortRouteRowStatus     RowStatus
        }

rc2kCpuEthernetPortRouteNetwork OBJECT-TYPE
        SYNTAX          IpAddress
        MAX-ACCESS      read-write
        STATUS          current
        DESCRIPTION     "Used to configure the network that can be
                        used to remotely manage this device."
        ::= { rc2kCpuEthernetPortRouteEntry 1 }

rc2kCpuEthernetPortRouteGateway OBJECT-TYPE
        SYNTAX          IpAddress
        MAX-ACCESS      read-write
        STATUS          current
        DESCRIPTION     "Used to configure the the IP address of the
                        gateway that should be used to forward IP
                        traffic."
        ::= { rc2kCpuEthernetPortRouteEntry 2 }

rc2kCpuEthernetPortRouteRowStatus OBJECT-TYPE
        SYNTAX        RowStatus
        MAX-ACCESS    read-write
        STATUS        current
        DESCRIPTION   "row status"
        ::= { rc2kCpuEthernetPortRouteEntry 3 }

-- 2k CPU card types
rc2kCPUTypeGeneralGroup OBJECT IDENTIFIER ::= { rc2k 12 }

rc2kCPUTypePrimary OBJECT-TYPE
           SYNTAX        INTEGER {
                                  cpu8690Default(1),
                                  cpu8690Upgrade(2),
                                  cpu8691Default(3),
                                  cpu8691Upgrade(4),
                                  cpu8692Default(5),
                                  cpu8692SuperMezz(6),
                                  cpu8695Default(7),
                                  cpu8895Default(8),
                                  undefined(255)
                                 }
           MAX-ACCESS     read-only
           STATUS               current
           DESCRIPTION   "This enum type will distinguish one CPU type from the other."
           ::= { rc2kCPUTypeGeneralGroup 1 }

rc2kCPUTypeSecondary OBJECT-TYPE
           SYNTAX          INTEGER {
                                  cpu8690Default(1),
                                  cpu8690Upgrade(2),
                                  cpu8691Default(3),
                                  cpu8691Upgrade(4),
                                  cpu8692Default(5),
                                  cpu8692SuperMezz(6),
                                  cpu8695Default(7),
                                  cpu8895Default(8),
                                  undefined(255)
                                 }
           MAX-ACCESS     read-only
           STATUS               current
           DESCRIPTION   "This type will distinguish one Secondary CPU type from the other."
           ::= { rc2kCPUTypeGeneralGroup 2 }

rc2kCPUTypePrimaryMemory OBJECT-TYPE
           SYNTAX              INTEGER {
                                      mem64MB(1),
                                      mem128MB(2),
                                      mem256MB(3),
                                      mem512MB(4),
                                      mem1024MB(5),
                                      undefined(255)
                                       }
          MAX-ACCESS     read-only
          STATUS               current
          DESCRIPTION   "This gives the memory size of the Primary CPU type."
          ::= { rc2kCPUTypeGeneralGroup 3 }

rc2kCPUTypeSecondaryMemory OBJECT-TYPE
           SYNTAX                INTEGER {
                                      mem64MB(1),
                                      mem128MB(2),
                                      mem256MB(3),
                                      mem512MB(4),
                                      mem1024MB(5),
                                      undefined(255)
                                       }
           MAX-ACCESS      read-only
           STATUS                current
           DESCRIPTION    "This gives the memory size of the Secondary CPU type."
           ::= { rc2kCPUTypeGeneralGroup 4 }

rc2kCpuEthernetPortIpv6RouteTable OBJECT-TYPE
        SYNTAX        SEQUENCE OF Rc2kCpuEthernetPortIpv6RouteEntry
        MAX-ACCESS    not-accessible
        STATUS        current
        DESCRIPTION   "2k CPU Ethernet Port Route table for Ipv6"
        ::= { rc2k 13 }

rc2kCpuEthernetPortIpv6RouteEntry OBJECT-TYPE
        SYNTAX        Rc2kCpuEthernetPortIpv6RouteEntry
        MAX-ACCESS    not-accessible
        STATUS        current
        DESCRIPTION   "Entry containing information of 2k CPU Ethernet Port Ipv6"
        INDEX         { rc2kCpuEthernetPortIpv6RouteNetwork,
                                 rc2kCpuEthernetPortIpv6RoutePrefixLength,
                                 rc2kCpuEthernetPortIpv6RouteGateway}
        ::= { rc2kCpuEthernetPortIpv6RouteTable 1 }

Rc2kCpuEthernetPortIpv6RouteEntry ::= SEQUENCE {
                rc2kCpuEthernetPortIpv6RouteNetwork       Ipv6Address,
                rc2kCpuEthernetPortIpv6RoutePrefixLength  INTEGER,
                rc2kCpuEthernetPortIpv6RouteGateway       Ipv6Address,
                rc2kCpuEthernetPortIpv6RouteRowStatus     RowStatus
        }

rc2kCpuEthernetPortIpv6RouteNetwork OBJECT-TYPE
        SYNTAX          Ipv6Address
        MAX-ACCESS      not-accessible
        STATUS          current
        DESCRIPTION     "Used to configure the ipv6 network that can be used to remotely manage this device."
        ::= { rc2kCpuEthernetPortIpv6RouteEntry 1 }

rc2kCpuEthernetPortIpv6RoutePrefixLength OBJECT-TYPE
     SYNTAX         INTEGER (0..128)
     MAX-ACCESS     not-accessible
     STATUS         current
     DESCRIPTION    "The length of the prefix (in bits)."
     ::= { rc2kCpuEthernetPortIpv6RouteEntry 2 }

rc2kCpuEthernetPortIpv6RouteGateway OBJECT-TYPE
        SYNTAX          Ipv6Address
        MAX-ACCESS      not-accessible
        STATUS          current
        DESCRIPTION     "Used to configure the the IPv6 address of the gateway that should be used to forward IPv6 traffic."
        ::= { rc2kCpuEthernetPortIpv6RouteEntry 3 }

rc2kCpuEthernetPortIpv6RouteRowStatus OBJECT-TYPE
        SYNTAX        RowStatus
        MAX-ACCESS    read-create
        STATUS        current
        DESCRIPTION   "row status"
        ::= { rc2kCpuEthernetPortIpv6RouteEntry 4 }

--
-- RTM Info for 8011co (Tripod) chassis
--
rc2kCardModTable OBJECT-TYPE
        SYNTAX        SEQUENCE OF Rc2kCardModEntry
        MAX-ACCESS    not-accessible
        STATUS        current
        DESCRIPTION   "RTM info table"
        ::= { rc2k 14 }

rc2kCardModEntry OBJECT-TYPE
        SYNTAX        Rc2kCardModEntry
        MAX-ACCESS    not-accessible
        STATUS        current
        DESCRIPTION   "Entry containing RTM information"
        INDEX         { rc2kCardModIndex }
        ::= { rc2kCardModTable 1 }

Rc2kCardModEntry ::= SEQUENCE {
                rc2kCardModIndex         Integer32,
                rc2kCardModPresent       TruthValue,
                rc2kCardModType          INTEGER,
                rc2kCardModDescription   DisplayString,
                rc2kCardModSerialNum     DisplayString,
                rc2kCardModHwVersion     DisplayString,
                rc2kCardModPartNumber    DisplayString,
                rc2kCardModDateCode      DisplayString,
                rc2kCardModDeviations    DisplayString,
                rc2kCardModCpldId        Integer32,
                rc2kCardModCpldRev       Integer32
        }

rc2kCardModIndex OBJECT-TYPE
        SYNTAX        Integer32 (1..11)
        MAX-ACCESS    not-accessible
        STATUS        current
        DESCRIPTION   "slot number."
        ::= { rc2kCardModEntry 1 }

rc2kCardModPresent OBJECT-TYPE
        SYNTAX        TruthValue
        MAX-ACCESS    read-only
        STATUS        current
        DESCRIPTION   "Indicates if the RTM in this slot is present" 
        DEFVAL        { false }
        ::= { rc2kCardModEntry 2 }

rc2kCardModType OBJECT-TYPE
        SYNTAX        INTEGER {
                        other(1),
                        lc(1627267328),         -- 0x60FE2100
                        cpu56(1627259136),      -- 0x60FE0100
                        cpur(1627263232)        -- 0x60FE1100
                        }
        MAX-ACCESS    read-only
        STATUS        current
        DESCRIPTION   "RTM type"
        ::= { rc2kCardModEntry 3 }

rc2kCardModDescription OBJECT-TYPE
        SYNTAX        DisplayString (SIZE (0..20))
        MAX-ACCESS    read-only
        STATUS        current
        DESCRIPTION   "RTM description"
        ::= { rc2kCardModEntry 4 }

rc2kCardModSerialNum OBJECT-TYPE
        SYNTAX        DisplayString (SIZE (0..20))
        MAX-ACCESS    read-only
        STATUS        current
        DESCRIPTION   "RTM serial number"
        ::= { rc2kCardModEntry 5 }

rc2kCardModHwVersion OBJECT-TYPE
        SYNTAX        DisplayString (SIZE (0..20))
        MAX-ACCESS    read-only
        STATUS        current
        DESCRIPTION   "RTM hardware version"
        ::= { rc2kCardModEntry 6 }

rc2kCardModPartNumber OBJECT-TYPE
        SYNTAX        DisplayString (SIZE (0..20))
        MAX-ACCESS    read-only
        STATUS        current
        DESCRIPTION   "RTM part number"
        ::= { rc2kCardModEntry 7 }

rc2kCardModDateCode OBJECT-TYPE
        SYNTAX        DisplayString (SIZE (0..20))
        MAX-ACCESS    read-only
        STATUS        current
        DESCRIPTION   "RTM date code"
        ::= { rc2kCardModEntry 8 }

rc2kCardModDeviations OBJECT-TYPE
        SYNTAX        DisplayString (SIZE (0..20))
        MAX-ACCESS    read-only
        STATUS        current
        DESCRIPTION   "RTM deviations"
        ::= { rc2kCardModEntry 9 }

rc2kCardModCpldId OBJECT-TYPE
        SYNTAX        Integer32 
        MAX-ACCESS    read-only
        STATUS        current
        DESCRIPTION   "RTM CPLD ID value"
        ::= { rc2kCardModEntry 10 }

rc2kCardModCpldRev    OBJECT-TYPE
        SYNTAX        Integer32 
        MAX-ACCESS    read-only
        STATUS        current
        DESCRIPTION   "RTM CPLD revision value"
        ::= { rc2kCardModEntry 11 }

--
-- COP Utilization
--
rc2kCardPerfTable OBJECT-TYPE
        SYNTAX        SEQUENCE OF Rc2kCardPerfEntry
        MAX-ACCESS    not-accessible
        STATUS        current
        DESCRIPTION   "This table represents the Card/Slot level DRAM
                       size, DRAM Used, DRAM Free and CPU Utilization
                       for the R Module and RC Module cards"
        ::= { rc2k 15 }

rc2kCardPerfEntry OBJECT-TYPE
        SYNTAX          Rc2kCardPerfEntry
        MAX-ACCESS      not-accessible
        STATUS          current
        DESCRIPTION    "Entry containing information of Card performance"
        INDEX                  { rc2kCardPerfId }
        ::= { rc2kCardPerfTable 1 }

Rc2kCardPerfEntry ::= SEQUENCE {
                rc2kCardPerfId                  INTEGER,
                rc2kCardPerfDramSize            Integer32,
                rc2kCardPerfDramUsed            Integer32,
                rc2kCardPerfDramFree            Integer32,
                rc2kCardPerfCPUUtilization      Integer32 
        }

rc2kCardPerfId OBJECT-TYPE
        SYNTAX           INTEGER (1..10)
        MAX-ACCESS       not-accessible
        STATUS           current
        DESCRIPTION      "This represents the slot number.
                          This is only for line cards, slot 5 and 6 should not be used."
        ::= { rc2kCardPerfEntry 1 }

rc2kCardPerfDramSize OBJECT-TYPE
        SYNTAX         Integer32
        MAX-ACCESS     read-only
        STATUS         current
        DESCRIPTION    "This represents DRAM Size in Mega bytes"
        ::= { rc2kCardPerfEntry 2 }

rc2kCardPerfDramUsed OBJECT-TYPE
        SYNTAX        Integer32 
        MAX-ACCESS    read-only
        STATUS        current
        DESCRIPTION   "This represents the amount of DRAM used in kilo bytes"
        ::= { rc2kCardPerfEntry 3 }

rc2kCardPerfDramFree OBJECT-TYPE
        SYNTAX        Integer32 
        MAX-ACCESS    read-only
        STATUS        current
        DESCRIPTION   "This represents the amount of DRAM Free in kilo bytes"
        ::= { rc2kCardPerfEntry 4 }

rc2kCardPerfCPUUtilization OBJECT-TYPE
        SYNTAX         Integer32
        MAX-ACCESS     read-only
        STATUS         current
        DESCRIPTION    "This represents the percentage of CPU utilization"
        ::= { rc2kCardPerfEntry 5 }

 rc2kSysAggrRateLimiterStatsTable OBJECT-TYPE
    SYNTAX        SEQUENCE OF Rc2kSysAggrRateLimiterStatsEntry
    MAX-ACCESS    not-accessible
    STATUS        current
    DESCRIPTION   "This table represents the Card/Slot level Aggregate rate limiter stats for power ranger cards."
    ::= { rc2k 16 }
 
 rc2kSysAggrRateLimiterStatsEntry OBJECT-TYPE
    SYNTAX        Rc2kSysAggrRateLimiterStatsEntry
    MAX-ACCESS    not-accessible
    STATUS        current
    DESCRIPTION   "Card/Slot level Aggregate rate limiter stats for power ranger cards indexed by slot number"
    INDEX         { rc2kSysAggrRateLimiterStatsId }
    ::= { rc2kSysAggrRateLimiterStatsTable 1 }
 
 Rc2kSysAggrRateLimiterStatsEntry ::= SEQUENCE {
    rc2kSysAggrRateLimiterStatsId              INTEGER,
    rc2kSysAggrRateLimiterIngGreenLane0        Integer32,
    rc2kSysAggrRateLimiterIngRedLane0          Integer32,
    rc2kSysAggrRateLimiterEgrGreenLane0        Integer32,
    rc2kSysAggrRateLimiterEgrRedLane0          Integer32,
    rc2kSysAggrRateLimiterIngGreenLane1        Integer32,
    rc2kSysAggrRateLimiterIngRedLane1          Integer32,
    rc2kSysAggrRateLimiterEgrGreenLane1        Integer32,
    rc2kSysAggrRateLimiterEgrRedLane1          Integer32,
    rc2kSysAggrRateLimiterIngGreenLane2        Integer32,
    rc2kSysAggrRateLimiterIngRedLane2          Integer32,
    rc2kSysAggrRateLimiterEgrGreenLane2        Integer32,
    rc2kSysAggrRateLimiterEgrRedLane2          Integer32,
    rc2kSysAggrRateLimiterStatsClear           Integer32
 }
 
 rc2kSysAggrRateLimiterStatsId OBJECT-TYPE
    SYNTAX           INTEGER (1..10)
    MAX-ACCESS       not-accessible
    STATUS           current
    DESCRIPTION      "This represents the slot number. This is only for line cards, slot 5 and 6 should not be used."
    ::= { rc2kSysAggrRateLimiterStatsEntry 1 }
 
 rc2kSysAggrRateLimiterIngGreenLane0 OBJECT-TYPE
    SYNTAX         Integer32
    MAX-ACCESS     read-only
    STATUS         current
    DESCRIPTION    "Number of packets passed or marked green by the Ingress Aggregate rate limiter"
    ::= { rc2kSysAggrRateLimiterStatsEntry 2 }
 
 rc2kSysAggrRateLimiterIngRedLane0 OBJECT-TYPE
    SYNTAX         Integer32
    MAX-ACCESS     read-only
    STATUS         current
    DESCRIPTION    "Number of packets dropped or marked red by the Ingress Aggregate rate limiter"
    ::= { rc2kSysAggrRateLimiterStatsEntry 3 }
                                                
 rc2kSysAggrRateLimiterEgrGreenLane0 OBJECT-TYPE
    SYNTAX         Integer32
    MAX-ACCESS     read-only
    STATUS         current
    DESCRIPTION    "Number of packets passed or marked green by the Egress Aggregate rate limiter"
    ::= { rc2kSysAggrRateLimiterStatsEntry 4 }
                                                               
 rc2kSysAggrRateLimiterEgrRedLane0 OBJECT-TYPE
    SYNTAX         Integer32
    MAX-ACCESS     read-only
    STATUS         current
    DESCRIPTION    "Number of packets dropped or marked red by the Egress Aggregate rate limiter"
    ::= { rc2kSysAggrRateLimiterStatsEntry 5 }
 
 
 rc2kSysAggrRateLimiterIngGreenLane1 OBJECT-TYPE
    SYNTAX         Integer32
    MAX-ACCESS     read-only
    STATUS         current
    DESCRIPTION    "Number of packets passed or marked green by the Ingress Aggregate rate limiter"
    ::= { rc2kSysAggrRateLimiterStatsEntry 6 }
 
 rc2kSysAggrRateLimiterIngRedLane1 OBJECT-TYPE
    SYNTAX         Integer32
    MAX-ACCESS     read-only
    STATUS         current
    DESCRIPTION    "Number of packets dropped or marked red by the Ingress Aggregate rate limiter"
    ::= { rc2kSysAggrRateLimiterStatsEntry 7 }
                                                
 rc2kSysAggrRateLimiterEgrGreenLane1 OBJECT-TYPE
    SYNTAX         Integer32
    MAX-ACCESS     read-only
    STATUS         current
    DESCRIPTION    "Number of packets passed or marked green by the Egress Aggregate rate limiter"
    ::= { rc2kSysAggrRateLimiterStatsEntry 8 }
                                                               
 rc2kSysAggrRateLimiterEgrRedLane1 OBJECT-TYPE
    SYNTAX         Integer32
    MAX-ACCESS     read-only
    STATUS         current
    DESCRIPTION    "Number of packets dropped or marked red by the Egress Aggregate rate limiter"
    ::= { rc2kSysAggrRateLimiterStatsEntry 9 }
 
 
 rc2kSysAggrRateLimiterIngGreenLane2 OBJECT-TYPE
    SYNTAX         Integer32
    MAX-ACCESS     read-only
    STATUS         current
    DESCRIPTION    "Number of packets passed or marked green by the Ingress Aggregate rate limiter"
    ::= { rc2kSysAggrRateLimiterStatsEntry 10 }
 
 rc2kSysAggrRateLimiterIngRedLane2 OBJECT-TYPE
    SYNTAX         Integer32
    MAX-ACCESS     read-only
    STATUS         current
    DESCRIPTION    "Number of packets dropped or marked red by the Ingress Aggregate rate limiter"
    ::= { rc2kSysAggrRateLimiterStatsEntry 11 }
                                                
 rc2kSysAggrRateLimiterEgrGreenLane2 OBJECT-TYPE
    SYNTAX         Integer32
    MAX-ACCESS     read-only
    STATUS         current
    DESCRIPTION    "Number of packets passed or marked green by the Egress Aggregate rate limiter"
    ::= { rc2kSysAggrRateLimiterStatsEntry 12 }
                                                               
 rc2kSysAggrRateLimiterEgrRedLane2 OBJECT-TYPE
    SYNTAX         Integer32
    MAX-ACCESS     read-only
    STATUS         current
    DESCRIPTION    "Number of packets dropped or marked red by the Egress Aggregate rate limiter"
    ::= { rc2kSysAggrRateLimiterStatsEntry 13 }
 
 rc2kSysAggrRateLimiterStatsClear OBJECT-TYPE
    SYNTAX         Integer32
    MAX-ACCESS     read-write
    STATUS         current
    DESCRIPTION    "Clear the Aggregate Rate limiter Stats"
    ::= { rc2kSysAggrRateLimiterStatsEntry 14 }

-- slot power usage info
 rc2kPowerConsumptionInfoTable OBJECT-TYPE
        SYNTAX        SEQUENCE OF Rc2kPowerConsumptionInfoEntry
        MAX-ACCESS    not-accessible
        STATUS        current
        DESCRIPTION   "Power consumption info table for all slots"
        ::= { rc2k 17 } 

rc2kPowerConsumptionInfoEntry OBJECT-TYPE
        SYNTAX        Rc2kPowerConsumptionInfoEntry
        MAX-ACCESS    not-accessible
        STATUS        current
        DESCRIPTION   "Entry containing power consumption information of
                        the slot"
        INDEX         { rc2kPowerConsumptionInfoIndex}
        ::= { rc2kPowerConsumptionInfoTable 1 }

Rc2kPowerConsumptionInfoEntry ::= SEQUENCE {
                rc2kPowerConsumptionInfoIndex            Integer32,
                rc2kPowerConsumptionInfoPowerStatus      INTEGER,
                rc2kPowerConsumptionInfoBasePower        Integer32,
                rc2kPowerConsumptionInfoConsumedPower    Integer32,
                rc2kPowerConsumptionInfoPowerPriority    INTEGER,
                rc2kPowerConsumptionInfoSlotDescription  DisplayString,
                rc2kPowerConsumptionInfoCardDescription  DisplayString
        }

rc2kPowerConsumptionInfoIndex OBJECT-TYPE
        SYNTAX          Integer32 (1..32)
        MAX-ACCESS      not-accessible
        STATUS          current
        DESCRIPTION     "Slot number."
        ::= { rc2kPowerConsumptionInfoEntry 1 }

rc2kPowerConsumptionInfoPowerStatus OBJECT-TYPE
        SYNTAX          INTEGER {
                                on(1),
                                off(2)
                        }
        MAX-ACCESS      read-only
        STATUS          current
        DESCRIPTION     "Power operation status of this slot"
        ::= { rc2kPowerConsumptionInfoEntry 2 }

rc2kPowerConsumptionInfoBasePower OBJECT-TYPE
        SYNTAX          Integer32
        MAX-ACCESS      read-only
        STATUS          current
        DESCRIPTION     "The base power required for this slot"
        ::= { rc2kPowerConsumptionInfoEntry 3 }

rc2kPowerConsumptionInfoConsumedPower OBJECT-TYPE
        SYNTAX          Integer32
        MAX-ACCESS      read-only
        STATUS          current
        DESCRIPTION     "The actual consumed power of this slot.
                        Value will be set zero when Power status is 'off'
                        rc2kPowerConsumptionInfoPowerStatus"
        ::= { rc2kPowerConsumptionInfoEntry 4 }

rc2kPowerConsumptionInfoPowerPriority OBJECT-TYPE
        SYNTAX          INTEGER
                        {
                           critical(1),
                           high(2),
                           low(3)
                        }
        MAX-ACCESS      read-only
        STATUS          current
        DESCRIPTION     "Used to indicate the priority of the slot for power
                         management"
        ::= { rc2kPowerConsumptionInfoEntry 5 }

rc2kPowerConsumptionInfoSlotDescription OBJECT-TYPE
        SYNTAX          DisplayString (SIZE (0..20))
        MAX-ACCESS      read-only
        STATUS          current
        DESCRIPTION     "User to indicate the slot type information.
                         Such as, 'Slot1'..'Slot12', 'SF1'..'SF4'..etc"
        ::= { rc2kPowerConsumptionInfoEntry 6 }

rc2kPowerConsumptionInfoCardDescription OBJECT-TYPE
        SYNTAX          DisplayString (SIZE (0..20))
        MAX-ACCESS      read-only
        STATUS          current
        DESCRIPTION     "Hardware description of this card"
        ::= { rc2kPowerConsumptionInfoEntry 7 }

--
-- Card Temperature MIB Table
--

rc2kTemperatureTable	OBJECT-TYPE
     SYNTAX SEQUENCE OF Rc2kTemperatureEntry
     MAX-ACCESS   not-accessible
     STATUS       current
     DESCRIPTION  "Table for retrieving the temperatures 
		   of each card (CP, IO, SF) on the chassis"
     ::= { rc2k 18 }

rc2kTemperatureEntry OBJECT-TYPE
     SYNTAX        Rc2kTemperatureEntry
     MAX-ACCESS    not-accessible
     STATUS        current
     DESCRIPTION   "Contains information regarding the temperature of
		    each slot (CP, IO and SF) on the chassis."
     INDEX        { rc2kTemperatureSlotIndex }
     ::= { rc2kTemperatureTable 1 }

Rc2kTemperatureEntry ::=
     SEQUENCE {
           rc2kTemperatureSlotIndex		Integer32,
           rc2kTemperatureSlotDescription	DisplayString,
	   rc2kTemperatureZone1Temperature	Gauge32,
	   rc2kTemperatureZone2Temperature	Gauge32,
	   rc2kTemperatureZone3Temperature	Gauge32,
	   rc2kTemperatureZone4Temperature	Gauge32,
	   rc2kTemperatureZone5Temperature	Gauge32,
	   rc2kTemperatureHighTemperature	Gauge32,
	   rc2kTemperatureLowTemperature	Gauge32,
	   rc2kTemperatureAlarmThreshold	Gauge32,
	   rc2kTemperatureShutdownThreshold	Gauge32
     }

rc2kTemperatureSlotIndex	OBJECT-TYPE
	SYNTAX		Integer32 (1..12 | 21..26)
	MAX-ACCESS	not-accessible
	STATUS		current
	DESCRIPTION	"Slot number of either a CP (1,2) or IO (3-12)
			 or SF (21-26)."
	::= { rc2kTemperatureEntry 1 }

rc2kTemperatureSlotDescription	OBJECT-TYPE
	SYNTAX		DisplayString (SIZE (0..20))
	MAX-ACCESS	read-only
	STATUS		current
	DESCRIPTION	"Used to indicate the slot type information.
                         Such as, 'Slot1'..'Slot12', 'SF1'..'SF4'..etc."
	::= { rc2kTemperatureEntry 2 }

rc2kTemperatureZone1Temperature	OBJECT-TYPE
	SYNTAX		Gauge32
	MAX-ACCESS	read-only
	STATUS		current
	DESCRIPTION	"Zone 1 temperature measured in celsius degree"
	::= { rc2kTemperatureEntry 3 }

rc2kTemperatureZone2Temperature	OBJECT-TYPE
	SYNTAX		Gauge32
	MAX-ACCESS	read-only
	STATUS		current
	DESCRIPTION	"Zone 2 temperature measured in celsius degree.
			 A value of 0 for this mib object indicates that
			 Zone 2 is not available on this slot."
	::= { rc2kTemperatureEntry 4 }

rc2kTemperatureZone3Temperature	OBJECT-TYPE
	SYNTAX		Gauge32
	MAX-ACCESS	read-only
	STATUS		current
	DESCRIPTION	"Zone 3 temperature measured in celsius degree.
			 A value of 0 for this mib object indicates that
			 Zone 3 is not available on this slot."
	::= { rc2kTemperatureEntry 5 }

rc2kTemperatureZone4Temperature	OBJECT-TYPE
	SYNTAX		Gauge32
	MAX-ACCESS	read-only
	STATUS		current
	DESCRIPTION	"Zone 4 temperature measured in celsius degree"
	::= { rc2kTemperatureEntry 6 }

rc2kTemperatureZone5Temperature	OBJECT-TYPE
	SYNTAX		Gauge32
	MAX-ACCESS	read-only
	STATUS		current
	DESCRIPTION	"Zone 5 temperature measured in celsius degree.
			 A value of 0 for this mib object indicates that
			 Zone 5 is not available on this slot."
	::= { rc2kTemperatureEntry 7 }

rc2kTemperatureHighTemperature	OBJECT-TYPE
	SYNTAX		Gauge32
	MAX-ACCESS	read-only
	STATUS		current
	DESCRIPTION	"Highest temperature measured in celsius degree"
	::= { rc2kTemperatureEntry 8 }

rc2kTemperatureLowTemperature	OBJECT-TYPE
	SYNTAX		Gauge32
	MAX-ACCESS	read-only
	STATUS		current
	DESCRIPTION	"Lowest temperature measured in celsius degree"
	::= { rc2kTemperatureEntry 9 }

rc2kTemperatureAlarmThreshold	OBJECT-TYPE
	SYNTAX		Gauge32
	MAX-ACCESS	read-only
	STATUS		current
	DESCRIPTION	"When the card temperature crosses this
			 threshold, an alarm will be set."
	::= { rc2kTemperatureEntry 10 }

rc2kTemperatureShutdownThreshold	OBJECT-TYPE
	SYNTAX		Gauge32
	MAX-ACCESS	read-only
	STATUS		current
	DESCRIPTION	"When the card temperature crosses this 
			 threshold, the card will be shutdown."
	::= { rc2kTemperatureEntry 11 }

--
-- USB MIB Table
--

rc2kUsbTable	OBJECT-TYPE
     SYNTAX SEQUENCE OF Rc2kUsbEntry
     MAX-ACCESS   not-accessible
     STATUS       current
     DESCRIPTION  "Table for retrieving the data for
		   the USBs inserted on the chassis"
     ::= { rc2k 19 }

rc2kUsbEntry OBJECT-TYPE
     SYNTAX        Rc2kUsbEntry
     MAX-ACCESS    not-accessible
     STATUS        current
     DESCRIPTION   "Contains information regarding the data for 
		    USBs inserted on the chassis"
     INDEX        { rc2kUsbSlotIndex }
     ::= { rc2kUsbTable 1 }

Rc2kUsbEntry ::=
     SEQUENCE {
           rc2kUsbSlotIndex             Integer32,
           rc2kUsbSlotDescription       DisplayString,
           rc2kUsbVendorId              DisplayString,
           rc2kUsbManufacturer          DisplayString,
           rc2kUsbProductId             DisplayString,
           rc2kUsbProductName           DisplayString,
           rc2kUsbSerialNumber          DisplayString,
           rc2kUsbRevision              DisplayString,
           rc2kUsbMaxCurrent            Integer32
     }

rc2kUsbSlotIndex	OBJECT-TYPE
	SYNTAX		Integer32 (1..2)
	MAX-ACCESS	not-accessible
	STATUS		current
	DESCRIPTION	"Slot number of CP in which USB is inserted."
	::= { rc2kUsbEntry 1 }

rc2kUsbSlotDescription	OBJECT-TYPE
	SYNTAX		DisplayString (SIZE (0..20))
	MAX-ACCESS	read-only
	STATUS		current
	DESCRIPTION	"Used to indicate the slot type information.
                         Such as, 'Slot1'..'Slot2."
	::= { rc2kUsbEntry 2 }

rc2kUsbVendorId	OBJECT-TYPE
	SYNTAX		DisplayString (SIZE (0..32))
	MAX-ACCESS	read-only
	STATUS		current
	DESCRIPTION	"Indicates the Vendor Id for the inserted USB.
                         Value is assigned by USB-IF."  
	::= { rc2kUsbEntry 3 }

rc2kUsbManufacturer	OBJECT-TYPE
	SYNTAX		DisplayString (SIZE (0..32))
	MAX-ACCESS	read-only
	STATUS		current
	DESCRIPTION	"Indicates the Manufacturer for the inserted USB."
	::= { rc2kUsbEntry 4 }

rc2kUsbProductId	OBJECT-TYPE
	SYNTAX		DisplayString (SIZE (0..32))
	MAX-ACCESS	read-only
	STATUS		current
	DESCRIPTION	"Indicates the Product Id for the inserted USB.
                         Value is assigned by manufacturer."
	::= { rc2kUsbEntry 5 }

rc2kUsbProductName	OBJECT-TYPE
	SYNTAX		DisplayString (SIZE (0..32))
	MAX-ACCESS	read-only
	STATUS		current
	DESCRIPTION	"Indicates the Product Name for the inserted USB."
	::= { rc2kUsbEntry 6 }

rc2kUsbSerialNumber	OBJECT-TYPE
	SYNTAX		DisplayString (SIZE (0..32))
	MAX-ACCESS	read-only
	STATUS		current
	DESCRIPTION	"Indicates the Serial Number for the inserted USB."
	::= { rc2kUsbEntry 7 }

rc2kUsbRevision         OBJECT-TYPE
	SYNTAX		DisplayString (SIZE (0..32))
	MAX-ACCESS	read-only
	STATUS		current
	DESCRIPTION	"Indicates the release number for the inserted USB."
	::= { rc2kUsbEntry 8 }

rc2kUsbMaxCurrent	OBJECT-TYPE
	SYNTAX		Integer32
        UNITS           "milliamps"            
	MAX-ACCESS	read-only
	STATUS		current
	DESCRIPTION	"Returns the Max Power as defined by specification  
                         for the inserted USB.  The units are milliamps."
	::= { rc2kUsbEntry 9 }


-- Forwarding Slice specific Asic Info Table.

rc2kCardAsicInfoTable OBJECT-TYPE
	SYNTAX        SEQUENCE OF Rc2kCardAsicInfoEntry
	MAX-ACCESS    not-accessible
	STATUS        current
	DESCRIPTION   "A table that contains asic information that 
		      is specific to a forwarding slice on a 
		      second generation IO module."
	::= { rc2k 20 }

rc2kCardAsicInfoEntry OBJECT-TYPE
	SYNTAX        Rc2kCardAsicInfoEntry
	MAX-ACCESS    not-accessible
	STATUS        current
	DESCRIPTION   "Second Generation Card attributes"
	INDEX         { rc2kCardAsicInfoIndex,
	                rc2kCardAsicInfoForwardingSlice }
	::= { rc2kCardAsicInfoTable 1 }

Rc2kCardAsicInfoEntry ::=
	SEQUENCE {
		rc2kCardAsicInfoIndex Integer32,
		rc2kCardAsicInfoForwardingSlice Integer32,
		rc2kCardAsicInfoQE DisplayString,
		rc2kCardAsicInfoZagrosFpga DisplayString,
		rc2kCardAsicInfoRsp DisplayString,
                rc2kCardAsicInfoPhyRev DisplayString
        }

rc2kCardAsicInfoIndex OBJECT-TYPE
        SYNTAX        	Integer32 (3..12)
        MAX-ACCESS     	not-accessible
        STATUS        	current
        DESCRIPTION   	"A unique value for each module within the chassis.
                      	This value is determined by the chassis slot number
                      	where the module is inserted.  Valid entries are 3
                      	to the value of rcChasNumSlots"
        ::= { rc2kCardAsicInfoEntry 1 }

rc2kCardAsicInfoForwardingSlice OBJECT-TYPE
        SYNTAX        	Integer32 (1..3)
        MAX-ACCESS     	not-accessible
        STATUS        	current
        DESCRIPTION   	"A unique value for each forwarding slice on the card."
        ::= { rc2kCardAsicInfoEntry 2 }

rc2kCardAsicInfoQE OBJECT-TYPE
        SYNTAX        DisplayString (SIZE (0..20))
        MAX-ACCESS    read-only
        STATUS        current
        DESCRIPTION   "QE version for the forwarding slice on IO card"
        ::= { rc2kCardAsicInfoEntry 3 }

rc2kCardAsicInfoZagrosFpga OBJECT-TYPE
        SYNTAX        DisplayString (SIZE (0..20))
        MAX-ACCESS    read-only
        STATUS        current
        DESCRIPTION   "Zagros FPGA for the forwarding slice on IO card"
        ::= { rc2kCardAsicInfoEntry 4 }

rc2kCardAsicInfoRsp OBJECT-TYPE
        SYNTAX        DisplayString (SIZE (0..20))
        MAX-ACCESS    read-only
        STATUS        current
        DESCRIPTION   "RSP for the forwarding slice on IO card" 
        ::= { rc2kCardAsicInfoEntry 5 }

rc2kCardAsicInfoPhyRev OBJECT-TYPE
        SYNTAX        DisplayString (SIZE (0..20))
        MAX-ACCESS    read-only
        STATUS        current
        DESCRIPTION   "PHY revision for the forwarding slice on IO card"
        ::= { rc2kCardAsicInfoEntry 6 }


-- IO Card (Generation 2) Temperature Table.

rc2kIoCardTemperatureTable	OBJECT-TYPE
	SYNTAX	SEQUENCE OF Rc2kIoCardTemperatureEntry
	MAX-ACCESS	not-accessible
	STATUS		current
	DESCRIPTION	"Table for retrieving the temperatures of the sensors
			located on the FPGA's and FA's on the generation 2
			IO cards."
	::= { rc2k 21 }

rc2kIoCardTemperatureEntry	OBJECT-TYPE
	SYNTAX		Rc2kIoCardTemperatureEntry
	MAX-ACCESS	not-accessible
	STATUS		current
	DESCRIPTION	"Contains information regarding the temperatures of 
			FPGA's and FA's on the generation 2 IO cards."
	INDEX		{ rc2kIoCardTemperatureSlotIndex }
	::= { rc2kIoCardTemperatureTable 1 }

Rc2kIoCardTemperatureEntry ::=
	SEQUENCE {
		rc2kIoCardTemperatureSlotIndex			Integer32,
		rc2kIoCardTemperatureFPGASensor1Temperature	Integer32,
		rc2kIoCardTemperatureFPGASensor2Temperature	Integer32,
		rc2kIoCardTemperatureFPGASensor3Temperature	Integer32,
		rc2kIoCardTemperatureFPGASensor4Temperature	Integer32,
		rc2kIoCardTemperatureFPGASensor5Temperature	Integer32,
		rc2kIoCardTemperatureFPGASensor6Temperature	Integer32,
		rc2kIoCardTemperatureFPGASensor7Temperature	Integer32,
		rc2kIoCardTemperatureFPGASensor8Temperature	Integer32,
		rc2kIoCardTemperatureFPGASensor9Temperature	Integer32,
		rc2kIoCardTemperatureFPGAZoneHighTemperature	Integer32,
		rc2kIoCardTemperatureFPGAZoneLowTemperature	Integer32,
		rc2kIoCardTemperatureFPGAZoneAlarmThreshold	Integer32,
		rc2kIoCardTemperatureFPGAZoneShutdownThreshold	Integer32,
		rc2kIoCardTemperatureFASensor1Temperature	Integer32,
		rc2kIoCardTemperatureFASensor2Temperature	Integer32,
		rc2kIoCardTemperatureFASensor3Temperature	Integer32,
		rc2kIoCardTemperatureFAZoneHighTemperature	Integer32,
		rc2kIoCardTemperatureFAZoneLowTemperature	Integer32,
		rc2kIoCardTemperatureFAZoneAlarmThreshold	Integer32,
		rc2kIoCardTemperatureFAZoneShutdownThreshold	Integer32
	}

rc2kIoCardTemperatureSlotIndex		OBJECT-TYPE
	SYNTAX		Integer32(3..12)
	MAX-ACCESS	not-accessible
	STATUS		current
	DESCRIPTION	"Slot number of the IO card"
	::= { rc2kIoCardTemperatureEntry 1 }

rc2kIoCardTemperatureFPGASensor1Temperature	OBJECT-TYPE
	SYNTAX		Integer32
	UNITS		"celsius"
	MAX-ACCESS	read-only
	STATUS		current
	DESCRIPTION	"Temperature of the FPGA Sensor 1, located on the
			Zagros on the first slice, measured in celsius degrees.
			A value of 0 for this mib object indicates that this
			sensor is not available on this slot."
	::= { rc2kIoCardTemperatureEntry 2 }

rc2kIoCardTemperatureFPGASensor2Temperature	OBJECT-TYPE
	SYNTAX		Integer32
	UNITS		"celsius"
	MAX-ACCESS	read-only
	STATUS		current
	DESCRIPTION	"Temperature of the FPGA Sensor 2, located on the
			Zagros on the first slice, measured in celsius degrees.
			A value of 0 for this mib object indicates that this
			sensor is not available on this slot."
	::= { rc2kIoCardTemperatureEntry 3 }

rc2kIoCardTemperatureFPGASensor3Temperature	OBJECT-TYPE
	SYNTAX		Integer32
	UNITS		"celsius"
	MAX-ACCESS	read-only
	STATUS		current
	DESCRIPTION	"Temperature of the FPGA Sensor 3, located on the
			RSP on the first slice, measured in celsius degrees.
			A value of 0 for this mib object indicates that this
			sensor is not available on this slot."
	::= { rc2kIoCardTemperatureEntry 4 }

rc2kIoCardTemperatureFPGASensor4Temperature	OBJECT-TYPE
	SYNTAX		Integer32
	UNITS		"celsius"
	MAX-ACCESS	read-only
	STATUS		current
	DESCRIPTION	"Temperature of the FPGA Sensor 4, located on the
			Zagros on the second slice, measured in celsius degrees.
			A value of 0 for this mib object indicates that this
			sensor is not available on this slot."
	::= { rc2kIoCardTemperatureEntry 5 }

rc2kIoCardTemperatureFPGASensor5Temperature	OBJECT-TYPE
	SYNTAX		Integer32
	UNITS		"celsius"
	MAX-ACCESS	read-only
	STATUS		current
	DESCRIPTION	"Temperature of the FPGA Sensor 5, located on the
			Zagros on the second slice, measured in celsius degrees.
			A value of 0 for this mib object indicates that this
			sensor is not available on this slot."
	::= { rc2kIoCardTemperatureEntry 6 }

rc2kIoCardTemperatureFPGASensor6Temperature	OBJECT-TYPE
	SYNTAX		Integer32
	UNITS		"celsius"
	MAX-ACCESS	read-only
	STATUS		current
	DESCRIPTION	"Temperature of the FPGA Sensor 6, located on the
			RSP on the second slice, measured in celsius degrees.
			A value of 0 for this mib object indicates that this
			sensor is not available on this slot."
	::= { rc2kIoCardTemperatureEntry 7 }

rc2kIoCardTemperatureFPGASensor7Temperature	OBJECT-TYPE
	SYNTAX		Integer32
	UNITS		"celsius"
	MAX-ACCESS	read-only
	STATUS		current
	DESCRIPTION	"Temperature of the FPGA Sensor 7, located on the
			Zagros on the third slice, measured in celsius degrees.
			A value of 0 for this mib object indicates that this
			sensor is not available on this slot."
	::= { rc2kIoCardTemperatureEntry 8 }

rc2kIoCardTemperatureFPGASensor8Temperature	OBJECT-TYPE
	SYNTAX		Integer32
	UNITS		"celsius"
	MAX-ACCESS	read-only
	STATUS		current
	DESCRIPTION	"Temperature of the FPGA Sensor 8, located on the
			Zagros on the third slice, measured in celsius degrees.
			A value of 0 for this mib object indicates that this
			sensor is not available on this slot."
	::= { rc2kIoCardTemperatureEntry 9 }

rc2kIoCardTemperatureFPGASensor9Temperature	OBJECT-TYPE
	SYNTAX		Integer32
	UNITS		"celsius"
	MAX-ACCESS	read-only
	STATUS		current
	DESCRIPTION	"Temperature of the FPGA Sensor 9, located on the
			RSP on the third slice, measured in celsius degrees.
			A value of 0 for this mib object indicates that this
			sensor is not available on this slot."
	::= { rc2kIoCardTemperatureEntry 10 }

rc2kIoCardTemperatureFPGAZoneHighTemperature	OBJECT-TYPE
	SYNTAX		Integer32
	UNITS		"celsius"
	MAX-ACCESS	read-only
	STATUS		current
	DESCRIPTION	"Highest temperature of all the FPGA sensors located 
			on this IO card, measured in celsius degrees."
	::= { rc2kIoCardTemperatureEntry 11 }

rc2kIoCardTemperatureFPGAZoneLowTemperature	OBJECT-TYPE
	SYNTAX		Integer32
	UNITS		"celsius"
	MAX-ACCESS	read-only
	STATUS		current
	DESCRIPTION	"Lowest temperature of all the FPGA sensors located 
			on this IO card, measured in celsius degrees."
	::= { rc2kIoCardTemperatureEntry 12 }

rc2kIoCardTemperatureFPGAZoneAlarmThreshold	OBJECT-TYPE
	SYNTAX		Integer32
	UNITS		"celsius"
	MAX-ACCESS	read-only
	STATUS		current
	DESCRIPTION	"When the FPGA temperature crosses this threshold 
			on this IO card, an alarm will be set."
	::= { rc2kIoCardTemperatureEntry 13 }

rc2kIoCardTemperatureFPGAZoneShutdownThreshold	OBJECT-TYPE
	SYNTAX		Integer32
	UNITS		"celsius"
	MAX-ACCESS	read-only
	STATUS		current
	DESCRIPTION	"When the FPGA temperature crosses this threshold 
			on this IO card, the card will be shutdown."
	::= { rc2kIoCardTemperatureEntry 14 }

rc2kIoCardTemperatureFASensor1Temperature	OBJECT-TYPE
	SYNTAX		Integer32
	UNITS		"celsius"
	MAX-ACCESS	read-only
	STATUS		current
	DESCRIPTION	"Temperature of the FA Sensor 1, located on the
			first slice, measured in celsius degrees.
			A value of 0 for this mib object indicates that this
			sensor is not available on this slot."
	::= { rc2kIoCardTemperatureEntry 15 }

rc2kIoCardTemperatureFASensor2Temperature	OBJECT-TYPE
	SYNTAX		Integer32
	UNITS		"celsius"
	MAX-ACCESS	read-only
	STATUS		current
	DESCRIPTION	"Temperature of the FA Sensor 2, located on the
			second slice, measured in celsius degrees.
			A value of 0 for this mib object indicates that this
			sensor is not available on this slot."
	::= { rc2kIoCardTemperatureEntry 16 }

rc2kIoCardTemperatureFASensor3Temperature	OBJECT-TYPE
	SYNTAX		Integer32
	UNITS		"celsius"
	MAX-ACCESS	read-only
	STATUS		current
	DESCRIPTION	"Temperature of the FA Sensor 3, located on the
			third slice, measured in celsius degrees.
			A value of 0 for this mib object indicates that this
			sensor is not available on this slot."
	::= { rc2kIoCardTemperatureEntry 17 }

rc2kIoCardTemperatureFAZoneHighTemperature	OBJECT-TYPE
	SYNTAX		Integer32
	UNITS		"celsius"
	MAX-ACCESS	read-only
	STATUS		current
	DESCRIPTION	"Highest temperature of all the FA sensors located 
			on this IO card, measured in celsius degrees."
	::= { rc2kIoCardTemperatureEntry 18 }

rc2kIoCardTemperatureFAZoneLowTemperature	OBJECT-TYPE
	SYNTAX		Integer32
	UNITS		"celsius"
	MAX-ACCESS	read-only
	STATUS		current
	DESCRIPTION	"Lowest temperature of all the FA sensors located 
			on this IO card, measured in celsius degrees."
	::= { rc2kIoCardTemperatureEntry 19 }

rc2kIoCardTemperatureFAZoneAlarmThreshold	OBJECT-TYPE
	SYNTAX		Integer32
	UNITS		"celsius"
	MAX-ACCESS	read-only
	STATUS		current
	DESCRIPTION	"When the FA temperature crosses this threshold 
			on this IO card, an alarm will be set."
	::= { rc2kIoCardTemperatureEntry 20 }

rc2kIoCardTemperatureFAZoneShutdownThreshold	OBJECT-TYPE
	SYNTAX		Integer32
	UNITS		"celsius"
	MAX-ACCESS	read-only
	STATUS		current
	DESCRIPTION	"When the FA temperature crosses this threshold 
			on this IO card, the card will be shutdown."
	::= { rc2kIoCardTemperatureEntry 21 }


-- Boot Config Host Table

rc2kBootConfigHostTable OBJECT-TYPE
    	SYNTAX          SEQUENCE OF Rc2kBootConfigHostEntry
	MAX-ACCESS      not-accessible
	STATUS          current
	DESCRIPTION     "Table for the bootconfig host info on the device"
	::= { rc2k 22 }

rc2kBootConfigHostEntry OBJECT-TYPE
        SYNTAX          Rc2kBootConfigHostEntry
	MAX-ACCESS	not-accessible
	STATUS		current
	DESCRIPTION	"Entry containing boot config host information."
	INDEX		{ rc2kBootConfigHostSlot }
	::= { rc2kBootConfigHostTable 1 }

Rc2kBootConfigHostEntry ::=
	SEQUENCE {
		rc2kBootConfigHostSlot			Integer32,
		rc2kBootConfigHostTftpHash		TruthValue,
		rc2kBootConfigHostTftpRetransmit	Integer32,
		rc2kBootConfigHostTftpTimeout		Integer32,
		rc2kBootConfigHostUser			DisplayString,
		rc2kBootConfigHostPassword		DisplayString
		}

rc2kBootConfigHostSlot OBJECT-TYPE
    	SYNTAX		Integer32(1..2)
	MAX-ACCESS	read-only
	STATUS		current
	DESCRIPTION	"slot number, VSP uses 1,2"
	::= { rc2kBootConfigHostEntry 1 }

rc2kBootConfigHostTftpHash OBJECT-TYPE
    	SYNTAX		TruthValue
	MAX-ACCESS	read-write
	STATUS		current
	DESCRIPTION	"Enables tftp hashing"
	DEFVAL		{ false }
	::= { rc2kBootConfigHostEntry 2 }

rc2kBootConfigHostTftpRetransmit OBJECT-TYPE
    	SYNTAX		Integer32(1..120)
	MAX-ACCESS	read-write
    STATUS		current
	DESCRIPTION	"Set tftp retransmit timeout counter"
	DEFVAL		{ 2 }
	::= { rc2kBootConfigHostEntry 3 }

rc2kBootConfigHostTftpTimeout OBJECT-TYPE
    	SYNTAX		Integer32(1..120)
	MAX-ACCESS	read-write
	STATUS		current
	DESCRIPTION	"Set tftp timeout counter"
	DEFVAL		{ 6 }
	::= { rc2kBootConfigHostEntry 4 }

rc2kBootConfigHostUser OBJECT-TYPE
    	SYNTAX		DisplayString (SIZE(0..16))
	MAX-ACCESS	read-write
	STATUS		current
	DESCRIPTION	"Configure host user"
	::= { rc2kBootConfigHostEntry 5 }

rc2kBootConfigHostPassword OBJECT-TYPE
    	SYNTAX		DisplayString (SIZE(0..16))
	MAX-ACCESS	read-write
	STATUS		current
	DESCRIPTION	"Configure host password"
	::= { rc2kBootConfigHostEntry 6 }

END
