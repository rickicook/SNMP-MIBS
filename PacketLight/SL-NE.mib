-- *****************************************************************
-- PacketLight SiteLight Network Element MIB
--
-- Nov 2000, Omri Viner
--
-- Copyright (c) 1999-2000 by PacketLight Ltd.
-- All rights reserved.
-- *****************************************************************

SL-NE-MIB DEFINITIONS ::= BEGIN

IMPORTS
	MODULE-IDENTITY, OBJECT-TYPE,
	enterprises, NOTIFICATION-TYPE 		FROM SNMPv2-SMI
	DisplayString, TruthValue	  		FROM SNMPv2-TC
	MODULE-COMPLIANCE, OBJECT-GROUP,
	NOTIFICATION-GROUP                  FROM SNMPv2-CONF
	InterfaceIndex		               	FROM IF-MIB;


packetlight MODULE-IDENTITY
	LAST-UPDATED "200009260000Z"
	ORGANIZATION "PacketLight Networks Ltd."
	CONTACT-INFO
		"Omri_Viner@PacketLight.com"
	DESCRIPTION
		"The MIB module is the root of the PL extension mibs."
	::= { enterprises 4515 }

sitelight 	OBJECT IDENTIFIER ::= { packetlight 1 }
plproduct 	OBJECT IDENTIFIER ::= { packetlight 100 }

-- Values for the sysObjectId

plne 		OBJECT IDENTIFIER ::= { plproduct 1 }  

pl404r 		OBJECT IDENTIFIER ::= { plne 404 }  	-- pl-400E Root
pl400e 		OBJECT IDENTIFIER ::= { pl404r 1 }  	-- pl-400E 

pl1000r 	OBJECT IDENTIFIER ::= { plne 1000 }  	-- pl-1000 Root
pl1000 		OBJECT IDENTIFIER ::= { pl1000r 1 }  	-- pl-1000 
pl1000e		OBJECT IDENTIFIER ::= { pl1000r 2 }  	-- pl-1000E (former PL-800) 
pl1000em	OBJECT IDENTIFIER ::= { pl1000r 3 }  	-- pl-1000EM  
pl1000ro	OBJECT IDENTIFIER ::= { pl1000r 4 }  	-- pl-1000RO  
pl1000tn	OBJECT IDENTIFIER ::= { pl1000r 5 }  	-- pl-1000TN  
pl1000te	OBJECT IDENTIFIER ::= { pl1000r 6 }  	-- pl-1000TE  
pl1000il	OBJECT IDENTIFIER ::= { pl1000r 7 }  	-- pl-1000IL  
pl1000tec	OBJECT IDENTIFIER ::= { pl1000r 8 }  	-- pl-1000TE Crypto  

pl2000r 	OBJECT IDENTIFIER ::= { plne 2000 }  	-- pl-2000 Root
pl2000  	OBJECT IDENTIFIER ::= { pl2000r 1 }  	-- pl-2000 

pl1000gr 	OBJECT IDENTIFIER ::= { plne 2100 }  	-- pl-1000G Root
pl1000gm  	OBJECT IDENTIFIER ::= { pl1000gr 1 }  	-- pl-1000GM 
pl1000gt  	OBJECT IDENTIFIER ::= { pl1000gr 2 }  	-- pl-1000GT 
pl1000t1  	OBJECT IDENTIFIER ::= { pl1000gr 3 }  	-- pl-1000T CFP to CFP
pl1000t2  	OBJECT IDENTIFIER ::= { pl1000gr 4 }  	-- pl-1000T CFP2 to CFP
pl1000t3  	OBJECT IDENTIFIER ::= { pl1000gr 5 }  	-- pl-1000T CFP2 to 2xCFP

pl1000nro 	OBJECT IDENTIFIER ::= { plne 2200 }  	-- New pl-1000NRO Root
pl1000ro1  	OBJECT IDENTIFIER ::= { pl1000nro 1 }  	-- pl-1000NRO Type A 
pl1000ro2  	OBJECT IDENTIFIER ::= { pl1000nro 2 }  	-- pl-1000NRO Type B 
pl1000ro3  	OBJECT IDENTIFIER ::= { pl1000nro 3 }  	-- pl-1000NRO Type C

pl1000d 	OBJECT IDENTIFIER ::= { plne 2300 }  	-- pl-1000D Root
pl1000d1  	OBJECT IDENTIFIER ::= { pl1000d 1 }  	-- pl-1000D Type A   
pl1000d2  	OBJECT IDENTIFIER ::= { pl1000d 2 }  	-- pl-1000D Type B (RAMAN)   

pl2000adr 	OBJECT IDENTIFIER ::= { plne 2400 }  	-- pl-2000AD Root
pl2000ad1  	OBJECT IDENTIFIER ::= { pl2000adr 1 }  	-- pl-2000AD Type A 
pl2000ad2  	OBJECT IDENTIFIER ::= { pl2000adr 2 }  	-- pl-2000AD Type B (Metro) 
pl2000ad3  	OBJECT IDENTIFIER ::= { pl2000adr 3 }  	-- pl-2000M 2x100G QSFP28 (Access) 

pl2000mr 	OBJECT IDENTIFIER ::= { plne 2500 }  	-- pl-2000M Root
pl2000m1  	OBJECT IDENTIFIER ::= { pl2000mr 1 }  	-- pl-2000M 1x200G QAM16
pl2000m2  	OBJECT IDENTIFIER ::= { pl2000mr 2 }  	-- 

pl2000dcr 	OBJECT IDENTIFIER ::= { plne 2600 }  	-- pl-2000DC Root
pl2000dc1  	OBJECT IDENTIFIER ::= { pl2000dcr 1 }  	-- pl-2000DC Type A

pl2000tr 	OBJECT IDENTIFIER ::= { plne 2700 }  	-- pl-2000T Root
pl2000t1  	OBJECT IDENTIFIER ::= { pl2000tr 1 }  	-- pl-2000T Type A

-- The root for the service mibs

slService 	OBJECT IDENTIFIER ::= { sitelight 1 }

END
