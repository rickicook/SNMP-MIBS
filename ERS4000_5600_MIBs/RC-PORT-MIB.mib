RC-PORT-MIB DEFINITIONS ::= BEGIN

IMPORTS
    MODULE-IDENTITY, OBJECT-TYPE, Integer32, Counter32, Counter64
        FROM SNMPv2-SMI
    TruthValue, DisplayString, MacAddress, RowStatus, TimeInterval
        FROM SNMPv2-TC
    InterfaceIndex
        FROM IF-MIB
    VrfIdentifier 
        FROM RC-VRF-MIB
    PolicyAppType
        FROM LLDP-MED-MIB
    rcPort, rcChassis, rcTest, rcStat, PortSet, EnableValue, IdList
        FROM RAPID-CITY;

rcPortMib MODULE-IDENTITY
       LAST-UPDATED     "201109130000Z"
       ORGANIZATION     "Bay Networks, Rapid-City Group"
       CONTACT-INFO     "Yu-Ten Lee
                          Postal:       Nortel Networks, Inc.
                                               4465 Great America Parkway
                                               Santa Clara, CA 95052-8185

                         Tel:           408-495-2560
                         Fax:          408-495-6680
                         E-mail:     ylee@nortelnetworks.com"

       DESCRIPTION      "Enterprise MIB for the Accelar product family."
      
       REVISION         "201109130000Z" -- 13 Sept 2011
       DESCRIPTION      "Version 80: Added rcPortVlacpFlapDetectEnable,
                                     rcPortVlacpFlapFrequency,
				     rcPortVlacpFlapInterval"
       
       REVISION         "201107290000Z" -- 29 July 2011
       DESCRIPTION      "Version 79: Added rcSFPplus(107) and rc10GBaseT(108)
                                     to rcPortType"
       
       REVISION         "201106160000Z" -- 16 June 2011
       DESCRIPTION      "Version 78: Added rcPortLosslessEnetTable, fix
                                     MAX-ACCESS for the Index"

       REVISION         "201105260000Z" -- 26 May 2011
       DESCRIPTION      "Version 77: Added rcPortRmonEnable and rcPortIpsecEnable"

       REVISION         "201101060000Z" -- 06 January 2011
       DESCRIPTION      "Version 76: Increased the size of rcPortBrouterVrfName."

       REVISION         "201009210000Z" -- 21 September 2010
       DESCRIPTION      "Version 75:  Added:Imported TC from LLDP-MED-MIB module."

       REVISION         "201009170000Z" -- 17 September 2010
       DESCRIPTION      "Version 74:  Added:rcLldpXMedLocMediaPolicyTable"
       
       REVISION         "201009130000Z" -- 13 September 2010
       DESCRIPTION      "Version 73:  Updated:
                                  rcPortEgressRateLimit,
                                  rcPortIngressRatePeak,
                                  rcPortIngressRateSvc in rcPortTable.
                                      Added:
                                  rcPortCpLimitPktRate,
                                  rcPortCpLimitShutDownEnable in rcPortTable.
                                      Removed:
                                  rcPortCpHighQos from rcPortTable.
                                      Added:
                                  rcStatPolicerTotalBytes,
                                  rcStatPolicerTotalPkts, 
                                  rcStatPolicerGreenBytes,
                                  rcStatPolicerYellowBytes,
                                  rcStatPolicerRedBytes in rcStatTable."
                                
       REVISION         "200910200000Z" -- 20 October 2009
       DESCRIPTION      "Version 72:  Added rcPortIngressRatePeak
                                            rcPortIngressRateSvc,
					    rcPortHighQos to rcPortTable."

       REVISION         "200906120000Z" -- 12 June 2009
       DESCRIPTION      "Version 70:  Added: rcPortServiceCardType  as rcPortEntry 107."

       REVISION         "200905210000Z" -- 21 May 2009
       DESCRIPTION      "Version 69:  Added:
                                    rcPortRemotePortShutdownLocalMacAddress
                                    rcPortRemotePortShutdownRemoteMacAddress"

       REVISION         "200904100000Z" -- 10 April 2009
       DESCRIPTION      "Version 68:  Removed rcPortRemotePortShutdownThreshold
                                              rcPortRemotePortShutdownRxSeqCnt.
                                      Added rcPortRemotePortShutdownHoldTimer
                                            rcPortRemotePortShutdownStatus."

       REVISION         "200903310000Z" -- 31 March 2009
       DESCRIPTION      "Version 65: Added rcPortDhcpOption82SubscriberId."

       REVISION         "200903120000Z" -- 12 March 2009
       DESCRIPTION      "Version 64: Added under RcPortEntry:
                                        rcPortCtrlPktDropLimitEnable,
                                        rcPortCtrlPktDropLimit,
                                        rcPortCtrlPktShutdownLimitEnable,
                                        rcPortCtrlPktShutdownLimit,
                                        rcPortCtrlPktShutdownRtExceeded,
                                        rcPortCtrlPktDropRtExceeded
                                     Added under RcStatEntry:
                                        rcStatCtrlPktRtLimitTotalCnt,
                                        rcStatCtrlPktRtLimitDropCnt"

       REVISION         "200903060000Z" -- 06 March 2009
       DESCRIPTION      "Version 63:  Added rcGbicCX(105) and rc10GbicCX(106)
                                      to rcPortType"

       REVISION         "200902200000Z" -- 20 February 2009
       DESCRIPTION      "Version 62: Resolved OID conflicts in rcPortType
                                     introduced in MERS v5.2.1.0 which is
                                     now released.  Moved rcGbic1300SeFx(98)
                                     to (104) as this object has not been
                                     released."

       REVISION         "200902090000Z" -- 09 February 2009
       DESCRIPTION      "Version 61:  SMIv2 cleanup.
                                      Added rcPortRemotePortShutdownTable."

       REVISION         "200812090000Z" -- 09 December 2008
       DESCRIPTION      "Version 60:Added rcGbic1300SeFx to rcPortType."

       REVISION         "200805180000Z" -- 18 May 2008
       DESCRIPTION      "Version 59: Imported IdList. Added rcPortVrfIdList, rcPortVrfNameList,
			rcPortBrouterVrfId, rcPortBrouterVrfName, rcPortVrfCount in sequence"

       REVISION         "200805160000Z" -- 16 May 2008
       DESCRIPTION      "Version 58: Added rcPortVrfIdList, rcPortVrfNameList, 
			rcPortBrouterVrfId, rcPortBrouterVrfName, rcPortVrfCount"

       REVISION         "200804280000Z" -- 28 April 2008
       DESCRIPTION      "Version 57: Imported Counter64 from SNMPv2-SMI"

       REVISION         "200803140000Z" -- 14 March 2008
       DESCRIPTION      "Version 56: Added rcPortCfmControlMep,
	                                   rcPortMtu,
					   rcPortMtuState" 	   

       REVISION         "200802110000Z" -- 11 Feb 2008
       DESCRIPTION      "Version 55: Modified rcPortUniPort to rcPortInterfaceType,
	                             Added rc10GbDWDMR(96), rc10GbDWDMW(97)" 	   

       REVISION         "200712040000Z" -- 04 Dec 2007
       DESCRIPTION      "Version 54: Modified rcPortCfmVid."	   

       REVISION         "200710180000Z" -- 18 Oct 2007
       DESCRIPTION      "Version 53: Added rcPortUniPort."

       REVISION         "200706120000Z" -- 12 Jun 2007
       DESCRIPTION      "Version 52: Add rcPortType - rc10GbLRM(95)."

       REVISION         "200706110000Z" -- 11 June 2007
       DESCRIPTION      "Version 51: Add rcPortClearCfmStats"   

       REVISION         "200705230000Z" -- 23 May 2007
       DESCRIPTION      "Version 50: Add rcPortType - rc1GbFD(94)."

       REVISION         "200705220000Z" -- 22 May 2007
       DESCRIPTION      "Version 49: Modified rcPortAutoNegAd DESCRIPTION."

       REVISION         "200704160000Z" -- 16 Apr 2007
       DESCRIPTION      "Version 48: Added rcStatPbtUnknownDropCount"

       REVISION         "200704130000Z" -- 13 Apr 2007
       DESCRIPTION      "Version 47: Removed a duplicate definition rcPortAutoNegAd (87)"

       REVISION         "200702260000Z" -- 26 Feb 2007
       DESCRIPTION      "Version 46: Added new SFP (66-93) to rcPorType,
				     Added rcPortUserLabel1 and rcPortUserLabel2"

       REVISION         "200702200000Z" -- 20 Feb 2007
       DESCRIPTION      "Version 45: Removed a duplicate definition"

       REVISION         "200612060000Z" -- 06 Dec 2006
       DESCRIPTION      "Version 44: Added rcPortCfmVid attribute"

       REVISION         "200611300000Z" -- 30 Nov 2006
       DESCRIPTION      "Version 43: Added rcPortAutoNegAd attribute"

       REVISION         "200611220000Z" -- 22 Nov 2006
       DESCRIPTION      "Version 42: Added 2 new mib attributes rcPortIngressRateLimit and rcPortIngressRateLimitState"

       REVISION         "200611150000Z" -- 15 Nov 2006
       DESCRIPTION      "Version 41: Added new mib object: rcPortClockSource"

       REVISION         "200607310000Z" -- 31 Jul 2006
       DESCRIPTION      "Version 40: Added new mibs rcPortPvid and rcPortTdp"

       REVISION         "200607200000Z" -- 20 Jul 2006
       DESCRIPTION      "Version 39: Added rcPortAdacStatus"

       REVISION         "200607130000Z" -- 13 Jul 2006
       DESCRIPTION      "Version 38: Added new mibs rcPortPcapAclFilterListSize,rcPortPcapAclFilterList and Updated rcPortPcapMode"

       REVISION         "200606050000Z" -- 05 Jun 2006
       DESCRIPTION      "Version 37: Added rcPortMepList and rcPortNumOfMep"

       REVISION         "200604190000Z" -- 19 Apr 2006
       DESCRIPTION      "Version 36: Added rcPortSmartAutoNegotiate"

       REVISION         "200602100000Z" -- 10 Feb 2006
       DESCRIPTION      "Version 35: Added objects rcPortLacpEntry 7-10"

       REVISION         "200602080000Z" -- 08 Feb 2006
       DESCRIPTION      "Version 34: Added to rcPortType"

       REVISION         "200601180000Z" -- 18 Jan 2006
       DESCRIPTION      "Version 33: Updated rcPortPoeMainPseExtnDeviceDetectType"

       REVISION         "200511150000Z" -- 15 Nov 2005
       DESCRIPTION      "Version 32: Added 3 objects to rcPortTable."

       REVISION         "200510130000Z" -- 13 Oct 2005
       DESCRIPTION      "Version 31: Added rcPortTrustDscp.  Updated the defval on rcPortRemoteMirroringEtherType"

       REVISION         "200508250000Z" -- 25 Aug 2005
       DESCRIPTION      "Version 30: Removed duplicate leaf rcPortVLacpPortState"

       REVISION         "200507200000Z" -- 20 July 2005
       DESCRIPTION      "Version 29: Added leaf rcPortVLacpPortState"

       REVISION         "200507150000Z" -- 15 July 2005
       DESCRIPTION      "Version 28: Added rc1000BaseTXPOE to rcPortType"

       REVISION         "200506220000Z" -- 22 June 2005
       DESCRIPTION      "Version 27: Added rcPortFlushFdbTable"

       REVISION         "200506100000Z" -- 10 June 2005
       DESCRIPTION      "Version 26: chaned rcPortName length to 225"

       REVISION         "200506070000Z" -- 7 June 2005
       DESCRIPTION      "Version 25: added attribute rcPortQinqEtherType to rcPortTable"

       REVISION         "200506010000Z" -- 1 June 2005
       DESCRIPTION      "Version 24: added objects for BPDU filtering"

       REVISION         "200504150000Z" -- 15 Apr 2005
       DESCRIPTION      "Version 23: added new port types for 10 Gb (58-62) to rcPortType"

       REVISION         "200502160000Z" -- 16 Feb 2005
       DESCRIPTION      "Version 22: changed range of rcPortPcapFilterList"

       REVISION         "200502040000Z" -- 04 Feb 2005
       DESCRIPTION      "Version 21: Added rcPortMgmtLinkTable"

       REVISION         "200501140000Z" -- 14 Jan 2005
       DESCRIPTION      "Version 20: Added support for 10Gig links."

       REVISION         "200412150000Z" -- 15 December 2004
       DESCRIPTION      "Version 19: Added rcPortEgressRateLimit and 
                               rcPortEgressRateLimitState to rcPortEntry"

       REVISION         "200412090000Z" -- 09 December 2004 
       DESCRIPTION      "Version 18: Fix typos and clean up revision history"

       REVISION         "200411240000Z" -- 24 November 2004 
       DESCRIPTION      "Version 17: Re-submitting previous request as changes are not
                         reflected"

       REVISION         "200411040000Z" -- 04 November 2004 
       DESCRIPTION      "Version 16: Added rcPortExtCplimitConf, rcPortExtCplimitUtilRate
                         under rcPortTable"

       REVISION         "200410110000Z" -- 11 October 2004 
       DESCRIPTION      "Version 15: rcPortType conflict: rc10GbNone is now (56).
                         Remove rcPort8021POverrideEnable (rcPortEntry 65) as we
                         will be using rcPortIeee8021POverrideEnable from PP8300."

       REVISION         "200409300001Z" -- 30 September 2004 
       DESCRIPTION      "Version 14: Add range for rcPortVlacpSessionIfIndex' &
                         rcPortVlacpSessionSesNumber."

       REVISION         "200409300000Z" -- 30 September 2004 
       DESCRIPTION      "Version 13: Add rcGbicBx to rcPortType"

       REVISION         "200409290000Z" -- 29 September 2004 
       DESCRIPTION      "Version 12:  Add range for
                         rcPortLacpFastPeriodicTime/SlowPeriodicTime,
                         rcPortVLacpFastPeriodicTime/SlowPeriodicTime "

       REVISION         "200409280000Z" -- 28 September 2004 
       DESCRIPTION      "Version 11:  Add missing REVISION cause. "

       REVISION         "200409220000Z" -- 22 September 2004 
       DESCRIPTION      "Version 10:  Change rc100BaseTXPOL to rc100BaseTXPOE. "

       REVISION         "200409210000Z" -- 21 September 2004 
       DESCRIPTION      "Version 10:  Added rcPort8021POverrideEnable attribute 
                         by Alka Malik. "

       REVISION         "200409080000Z" -- 08 September 2004 
       DESCRIPTION      "Version 9:  Added rcPortAutoRecoverPort 
                         to RcPortEntry "

       REVISION         "200409010000Z" -- 01 Sept 2004 
       DESCRIPTION      "Version 8:  Added rcPortPoeMainPseExtnPwrLimit 
                         to rcPortPoeMainPseExtnTable"

       REVISION         "200408030000Z" -- 03 August 2004 
       DESCRIPTION      "Version 7:  Added rcPortVlacpSessionTable by Amit Singh. Also, 
                         there was a mismatch in MRT submission for rcPortPoe
                         (rcPort 7 versus rcPort 3 (correct)."

       REVISION         "200407230000Z" -- 23 July 2004 
       DESCRIPTION      "Version 6:  Added rcPortVLacpPortState to rcPortVLacpTable,
                         move rcPortVLacpDualHomingEnable to .10 (it was erroneously
                         defined as .9 when it was added)."

       REVISION         "200407220000Z" -- 22 July 2004 
       DESCRIPTION      "Version 5:  Added rcPortAutoNegAd and rcPortAutoNegAdCapability
                         to rcPortTable"

       REVISION         "200407070000Z" -- 7 July 2004 
       DESCRIPTION      "Version 4:  Added rcPortVLacpDualHomingEnable to
                         rcPortVLacpTable" 
			        
       ::= { rcPort 0 }

-- Port Table

rcPortTable OBJECT-TYPE
        SYNTAX	      SEQUENCE OF RcPortEntry
        MAX-ACCESS    not-accessible
        STATUS        current
        DESCRIPTION   "Port table"
        ::= { rcPort 1 }

rcPortEntry OBJECT-TYPE
        SYNTAX        RcPortEntry
        MAX-ACCESS    not-accessible
        STATUS        current
        DESCRIPTION   "Entry containing info. for a particular port"
        INDEX         { rcPortIndex }
        ::= { rcPortTable 1 }

RcPortEntry ::= SEQUENCE {
    rcPortIndex                           InterfaceIndex,
    rcPortType                            INTEGER,
    rcPortConnectorType                   INTEGER,
    rcPortPerformRouting                  TruthValue,
    rcPortHighPriority                    TruthValue,
    rcPortAction                          INTEGER,
    rcPortResult                          INTEGER,
    rcPortPrimaryConnector                INTEGER,
    rcPortActiveConnector                 INTEGER,
    rcPortBackupConnectorStatus           INTEGER,
    rcPortAutoNegotiate                   TruthValue,
    rcPortAdminDuplex                     INTEGER,
    rcPortOperDuplex                      INTEGER,
    rcPortAdminSpeed                      INTEGER,
    rcPortOperSpeed                       Integer32,
    rcPortMltId                           Integer32,
    rcPortLocked                          TruthValue,
    rcPortAutoNegotiationSupported        TruthValue,
    rcPortSingleRoutablePort              TruthValue,
    rcPortUnknownMacDiscard               TruthValue,
    rcPortNumStateTransition              Counter32,
    rcPortUserPriority                    INTEGER,
    rcPortAllowOversizeFrame              TruthValue,
    rcPortQosLevel                        INTEGER,
    rcPortDiffServEnable                  TruthValue,
    rcPortDiffServType                    INTEGER,
    rcPortDiffServIeee8021POverrideEnable TruthValue,
    rcPortVendorDescr                     DisplayString,
    rcPortName                            DisplayString,
    rcPortOctapidId                       Integer32,
    rcPortWan                             INTEGER,
    rcPortTransport                       INTEGER,
    rcPortMultimediaFilterEnable          TruthValue,
    rcPortMultimediaDevSelection          DisplayString,
    rcPortServiceType		          INTEGER, 
    rcPortMode			          INTEGER, 
    rcPortAdminRouting                    EnableValue,
    rcPortOperRouting                     EnableValue,
    rcPortPid                             Integer32,
    rcPortIeee8021POverrideEnable         TruthValue,
    rcPortShaperEnable                    TruthValue,
    rcPortShaperMaxRate                   Integer32,
    rcPortShaperBurstSize                 Integer32,
    rcPortCpLimitShutDown                 TruthValue,
    rcPortHighSecureEnable	          TruthValue,
    rcPortTlsPriorityOverride             EnableValue,
    rcPortVctAbility                      INTEGER,
    rcPortVctAdminStatus                  EnableValue,
    rcPortMrouteStrLimit                  Integer32,
    rcPortMrouteStrTimerCheck             Integer32,
    rcPortMrouteStrLimitEnable            TruthValue,
    rcPortUpdateDynamicMacQosLevel        EnableValue,
    rcPortVplsDualHoming                  INTEGER,
    rcPortVplsMgmtVlan                    TruthValue,
    rcPortTlsManagedBySp                  TruthValue,
    rcPortAutoNegAd                       BITS,
    rcPortAutoNegAdCapability             BITS,
    rcPortAutoRecoverPort                 TruthValue,
    rcPortExtCplimitConf                  INTEGER,
    rcPortExtCplimitUtilRate              Integer32,
    rcPortEgressRateLimit                 Integer32,
    rcPortEgressRateLimitState            EnableValue,
    rcPortBpduFilteringTimerCount         TimeInterval,
    rcPortBpduFilteringTimeout            TimeInterval,
    rcPortBpduFilteringAdminEnabled       TruthValue,
    rcPortBpduFilteringOperEnabled        TruthValue,
    rcPortQinqEtherType                   Integer32,
    rcPortTrustDscp                          TruthValue,
    rcPortCpLimitEnable                   EnableValue,
    rcPortCpMulticastLimit                Integer32,
    rcPortCpBroadcastLimit                Integer32,
    rcPortSmartAutoNegotiate              TruthValue,
    rcPortMepList                         OCTET STRING,
    rcPortNumOfMep                        Integer32,
    rcPortAdacStatus                      TruthValue,
    rcPortPvid                            Integer32,
    rcPortTdp                             EnableValue,
    rcPortClockSource                     INTEGER,
    rcPortIngressRateLimit                Integer32,
    rcPortIngressRateLimitState           EnableValue,
    rcPortVrfIdList                       IdList,
    rcPortCfmVid                          Integer32,
    rcPortUserLabel1	                  DisplayString,
    rcPortUserLabel2	                  DisplayString,
    rcPortClearCfmStats                   TruthValue,
    rcPortInterfaceType                   INTEGER,
    rcPortCfmControlMep                   DisplayString,
    rcPortMtu                             Integer32,
    rcPortMtuState                        EnableValue,
    rcPortVrfNameList                     OCTET STRING,
    rcPortBrouterVrfId                    VrfIdentifier,
    rcPortBrouterVrfName                  DisplayString,
    rcPortVrfCount                        Counter32,
    rcPortCtrlPktDropLimitEnable          EnableValue,  
    rcPortCtrlPktDropLimit                Integer32,
    rcPortCtrlPktShutdownLimitEnable      EnableValue,
    rcPortCtrlPktShutdownLimit            Integer32,
    rcPortCtrlPktShutdownRtExceeded       TruthValue,
    rcPortCtrlPktDropRtExceeded           TruthValue,
    rcPortDhcpOption82SubscriberId        DisplayString,
    rcPortServiceCardType                 INTEGER,
    rcPortIngressRatePeak		  INTEGER,
    rcPortIngressRateSvc		  INTEGER,
    rcPortCpLimitPktRate                  INTEGER,
    rcPortCpLimitShutDownEnable           TruthValue,
    rcPortRmonEnable                      TruthValue,
    rcPortIpsecEnable                     TruthValue
}

rcPortIndex OBJECT-TYPE
        SYNTAX        InterfaceIndex
        MAX-ACCESS    read-only
        STATUS        current
        DESCRIPTION   "An index value that uniquely identifies a port.
                      This value is similar to ifIndex in MIB2."
        ::= { rcPortEntry 1 }

rcPortType OBJECT-TYPE
	SYNTAX        INTEGER {
                         other(0),           -- no port installed
                         rc100BaseTX(1),     -- (cat 5)
                         rc100BaseT2(2),     -- (cat 3)
                         rc100BaseF(3),      -- (100 mbps fiber)
                         rc1000BaseF(4),     -- (1000 mbps fiber)
                         rc1000BaseDualF(5), -- (fiber - dual connector)
                         rc10BaseF(6),       -- (10 mbps fiber)
                         rcPosMMF(7),        -- (multi mode fiber)
                         rcPosSMF(8),        -- (single mode fiber)
                         rcAtm(9),           -- (oc3, oc12, ds3, e3)
                         rcGbicLx(10),       -- (gigabit long haul)
                         rcGbicSx(11),       -- (gigabit short haul)
                         rcGbicXd(12),       -- (gigabit extended distance)
                         rcGbicCu(13),       -- (gigabit copper)
                         rcGbicOther(14),    -- (gigabit other)
                         rcOc3cSM(15),       -- (OC-3c SM)
                         rcOc3cMM(16),       -- (OC-3c MM)
                         rcOc3cCOPPER(17),   -- (OC-3c COPPER)
                         rcOc12cSM(18),      -- (OC-12c SM)
                         rcOc12cMM(19),      -- (OC-12c MM)
                         rcDs3(20),          -- (Ds3)
                         rcE3(21),           -- (E3)
                         rcGbicNone(22),     -- (Gbic card feature)
                         rc1000BaseT(23),    -- (1000 base copper)
                         rcGbicZx(24),       -- (gigabit very extended distance)
                         rcOc3cAtmSM(25),    -- (Atm OC-3c SM)
                         rcOc3cAtmMM(26),    -- (Atm OC-3c MM)
                         rcOc12cAtmSM(27),   -- (Atm OC-12c SM)
                         rcOc12cAtmMM(28),   -- (Atm OC-12c MM)
                         rcOc3cPosSM(29),    -- (Pos OC-3c SM)
                         rcOc3cPosMM(30),    -- (Pos OC-3c MM)
                         rcOc12cPosSM(31),   -- (Pos OC-12c SM)
                         rcOc12cPosMM(32),   -- (Pos OC-12c MM)
                         rcGbic1470(33),     -- (gigabit wavelength 1470)
                         rcGbic1490(34),     -- (gigabit wavelength 1490)
                         rcGbic1510(35),     -- (gigabit wavelength 1510)
                         rcGbic1530(36),     -- (gigabit wavelength 1530)
                         rcGbic1550(37),     -- (gigabit wavelength 1550)
                         rcGbic1570(38),     -- (gigabit wavelength 1570)
                         rcGbic1590(39),     -- (gigabit wavelength 1590)
                         rcGbic1610(40),     -- (gigabit wavelength 1610)
                         rcRmon(41),         -- (1000 base TProbe)
                         rcGbic1470APD(42),  -- (gigabit wavelength 1470-APD)
                         rcGbic1490APD(43),  -- (gigabit wavelength 1490-APD)
                         rcGbic1510APD(44),  -- (gigabit wavelength 1510-APD)
                         rcGbic1530APD(45),  -- (gigabit wavelength 1530-APD)
                         rcGbic1550APD(46),  -- (gigabit wavelength 1550-APD)
                         rcGbic1570APD(47),  -- (gigabit wavelength 1570-APD)
                         rcGbic1590APD(48),  -- (gigabit wavelength 1590-APD)
                         rcGbic1610APD(49),  -- (gigabit wavelength 1610-APD)
	    		 rc10GbLW(50),       -- (10 Gig Ethernet LW)
	    		 rc10GbLR(51),        -- (10 Gig Ethernet LR)
                         rcLogicalServerPort(52), -- opm Prism used as a server for MPLS
                         rc1000BaseTX(53),   -- (triple speed)
                         rc100BaseTXPOE(54), -- (double speed with POE support)
                         rcGbicBx(55),       -- (gigabit medium haul)
                         rc10GbNone(56),     -- (10 Gig Feature)
                         rc1000XFP(57),      -- 10Gig XFP Gbic
                         rc10GbSR(58),       -- (10 Gig SR Ethernet)
                         rc10GbSW(59),       -- (10 Gib SW wavelength 850nm and sonet)
                         rc10GbER(60),       -- (10 Gig ER wavelen 1550nm)
                         rc10GbEW(61),       -- (10 Gig EW)
                         rc10GbOther(62),     -- (10 Gig Ethernet other)
                         rc1000BaseTXPOE(63),  -- (triple speed with POE support)
                         rc10GbZR(64),          -- (10G Python XFP, LAN)
                         rc10GbZW(65),          -- (10G Python XFP, WAN)
                         rcGbic1310Xd(66),   -- (gigabit wavelength 1310-distance 40Kms)
                         rcGbic1470Xd(67),   -- (gigabit wavelength 1470-distance 40Kms)
                         rcGbic1490Xd(68),   -- (gigabit wavelength 1490-distance 40Kms)
                         rcGbic1510Xd(69),   -- (gigabit wavelength 1510-distance 40Kms)
                         rcGbic1530Xd(70),   -- (gigabit wavelength 1530-distance 40Kms)
                         rcGbic1550Xd(71),   -- (gigabit wavelength 1550-distance 40Kms)
                         rcGbic1570Xd(72),   -- (gigabit wavelength 1570-distance 40Kms)
                         rcGbic1590Xd(73),   -- (gigabit wavelength 1590-distance 40Kms)
                         rcGbic1610Xd(74),   -- (gigabit wavelength 1610-distance 40Kms)
                         rcGbic1470Zx(75),   -- (gigabit wavelength 1470-distance 70Kms)
                         rcGbic1490Zx(76),   -- (gigabit wavelength 1490-distance 70Kms)
                         rcGbic1510Zx(77),   -- (gigabit wavelength 1510-distance 70Kms)
                         rcGbic1530Zx(78),   -- (gigabit wavelength 1530-distance 70Kms)
                         rcGbic1550Zx(79),   -- (gigabit wavelength 1550-distance 70Kms)
                         rcGbic1570Zx(80),   -- (gigabit wavelength 1570-distance 70Kms)
                         rcGbic1590Zx(81),   -- (gigabit wavelength 1590-distance 70Kms)
                         rcGbic1610Zx(82),   -- (gigabit wavelength 1610-distance 70Kms)
                         rcGbic1690Zx(83),   -- (gigabit wavelength 1690-distance 70Kms)
                         rcGbic1310Bx(84),   -- (gigabit wavelength 1310-distance 10Kms)
                         rcGbic1490Bx(85),   -- (gigabit wavelength 1490-distance 10Kms)
                         rcGbicEx(86),     -- (gigabit wavelength 1550-distance 120 Kms)
                         rcGbic850Sx(87),   -- (gigabit short haul wavelength 850)
                         rcGbic1200Lx(88),   -- (gigabit long haul wavelength 1200)
                         rcGbic1300Lx(89),   -- (gigabit long haul wavelength 1300)
                         rcGbic1310Lx(90),   -- (gigabit long haul wavelength 1310)
                         rcGbic1490Lx(91),   -- (gigabit long haul wavelength 1490)
                         rcGbic1550Lx(92),   -- (gigabit long haul wavelength 1550)
                         rcGbic1550Ex(93),   -- (gigabit wavelength 1550-distance 120Kms)
                         rc1GbFD(94),        -- (100/1000 Fiber Gbic)
                         rc10GbLRM(95),      --(10 Gig LRM)
	   		 rc10GbDWDMR(96),    -- (10 Gig DWDM Ethernet)
	   		 rc10GbDWDMW(97),    -- (10 Gig DWDM Sonet)
                         rc100BaseSX(98),    -- (100 mbps fiber short haul wavelength)
                         rc100BaseLX(99),    -- (100 mbps fiber long haul wavelength)
                         rc100BaseFX(100),   -- (100 mbps fiber)
                         rc100BaseBX(101),   -- (100 mbps fiber)
                         rc100BaseZX(102),   -- (100 mbps fiber)
	                 rcGbicMTRJ(103),    -- (Mechanical Transfer - registered jack)
 	   		 rcGbic1300SeFx(104),-- (1300SE-FX Gbic Ethernet)
			 rcGbicCX(105),      -- (copper direct attach cable up to 15 meter)
			 rc10GbicCX(106),    -- (copper direct attach cable up to 15 meter)
			 rcSFPplus(107),     -- (1000/10G SFP+ Gbic)
			 rc10GBaseT(108)     -- (100/1000/10G base copper)
	              }
	MAX-ACCESS    read-only
	STATUS        current
	DESCRIPTION   "Port type"
	::= { rcPortEntry 2 }

rcPortConnectorType OBJECT-TYPE
        SYNTAX        INTEGER {
                         nonRedundant(1), -- non-redundant connector type 
                         redundant(2) 	  -- redundant connector type 
                      }
        MAX-ACCESS    read-only
        STATUS        current
        DESCRIPTION   "Type of connector installed on this port."
        DEFVAL        { nonRedundant }
        ::= { rcPortEntry 3 }

rcPortPerformRouting OBJECT-TYPE
	SYNTAX 	      TruthValue
	MAX-ACCESS 	  read-write
        STATUS 	      deprecated
	DESCRIPTION   "Indicate whether this port should perform
                      routing"
	DEFVAL	      { false }
	::= { rcPortEntry 4 }

rcPortHighPriority OBJECT-TYPE 
        SYNTAX 	      TruthValue
        MAX-ACCESS 	  read-write
        STATUS 	      deprecated
        DESCRIPTION   "Indicate whether this port should be treated with 
                      high priority"
	DEFVAL 	      { false }
        ::= { rcPortEntry 5 }

rcPortAction OBJECT-TYPE
        SYNTAX        INTEGER {
                         none(1),            -- none of the following
                         flushMacFdb(2),     -- flush MAC forwarding table
                         flushArp(3),        -- flush ARP table
                         flushIp(4),         -- flush IP route table
                         flushAll(5),        -- flush all tables
			 triggerRipUpdate(6), -- manually trigger rip update
			 clearLoopDetectAlarm(7) -- manually enable the port on all the disabled vlans
                      }
        MAX-ACCESS    read-write
        STATUS        current
        DESCRIPTION   "Port related actions."
        DEFVAL        { none }
        ::= { rcPortEntry 6 }
 
rcPortResult OBJECT-TYPE 
        SYNTAX        	INTEGER { 
                       		none(1),        -- none of the following 
                       	  	inProgress(2),  -- in progress 
                       	  	success(3),     -- success
                       	  	fail(4)         -- failure 
                      	} 
        MAX-ACCESS		read-only 
        STATUS        	current 
        DESCRIPTION   	"Result from the last Vlan action." 
        DEFVAL        	{ none } 
        ::= { rcPortEntry 7 } 

rcPortPrimaryConnector OBJECT-TYPE 
        SYNTAX 		INTEGER { 
                		left(1),	-- left side connector
                		right(2),	-- right side connector 
				other(3)
        		} 
        MAX-ACCESS      read-write 
        STATUS          current 
        DESCRIPTION     "For ports configured with redundant connectors,
                         this value is used to indicate which connector 
                         should be used as the 'active' connector on this 
                         port the next time the port is placed into the 
                         ifAdminStatus=Up."
	       DEFVAL          { left } 
        ::= { rcPortEntry 8 }

rcPortActiveConnector OBJECT-TYPE
        SYNTAX        INTEGER {
                         	left(1),	-- left side connector
                         	right(2),       -- right side connector
				other(3)
                      }
        MAX-ACCESS    read-only
        STATUS        current 
        DESCRIPTION   "For ports configured with redundant connectors,
		      this value is used to indicate which connector
		      is currently the active one.  Only one connector
		      can be active an anytime."
        DEFVAL        { left } 
        ::= { rcPortEntry 9 }

rcPortBackupConnectorStatus OBJECT-TYPE
        SYNTAX 		INTEGER {
                		up(1),            -- link Up
                		down(2),          -- link Down
				other(3)
        }
        MAX-ACCESS      read-only
        STATUS          current
        DESCRIPTION     "Indicate the status of the link attached to the
		 	 back-up (non-active) connector."
        ::= { rcPortEntry 10 }

rcPortAutoNegotiate OBJECT-TYPE
        SYNTAX 	      TruthValue
        MAX-ACCESS 	  read-write
        STATUS 	      current
        DESCRIPTION   "Indicate whether this port enabled for auto 
                       negotiations or not."
        DEFVAL	      { true }
	       ::= { rcPortEntry 11 }

rcPortAdminDuplex OBJECT-TYPE
        SYNTAX 		INTEGER { 
                      half(1),	-- half duplex
                      full(2)		-- full duplex  
        		      } 
        MAX-ACCESS 		read-write
        STATUS 		current
        DESCRIPTION     "Indicates the port duplex type "	
        DEFVAL		{ half }
        ::= { rcPortEntry 12 }

rcPortOperDuplex OBJECT-TYPE
        SYNTAX     INTEGER { 
                      half(1),	-- half duplex
                      full(2)		-- full duplex  
                   } 
        MAX-ACCESS 		read-only
        STATUS 		current
        DESCRIPTION 	"Indicate this port's current duplex value."
        ::= { rcPortEntry 13 }

rcPortAdminSpeed OBJECT-TYPE
        SYNTAX     INTEGER { 
                      none(0),
                      mbps10(1),	-- 10Mb/s
                      mbps100(2),	-- 100Mb/s
                      mbps1000(3),      -- 1000Mb/s
                      mbps10000(4)      -- 10Gb/s
                   } 
        MAX-ACCESS 		read-write
        STATUS 		current
        DESCRIPTION 	"Indicate this port's speed."
        DEFVAL		{ mbps10 }
        ::= { rcPortEntry 14 }

rcPortOperSpeed OBJECT-TYPE
        SYNTAX       Integer32  
        MAX-ACCESS   read-only
        STATUS       current
        DESCRIPTION  "Indicate this port's current speed value."
	       ::= { rcPortEntry 15 }

rcPortMltId OBJECT-TYPE
        SYNTAX       Integer32  
        MAX-ACCESS   read-only
        STATUS       current
        DESCRIPTION  "Indicate which multi-link trunk (MLT) this port
                      is assigned to.  If this port is not associated
                      with any MLT, this value will be set to zero(0)."
        DEFVAL		{ 0 }
        ::= { rcPortEntry 16 }

rcPortLocked OBJECT-TYPE
        SYNTAX        	TruthValue
        MAX-ACCESS        	read-only
        STATUS        	current
        DESCRIPTION   	"Indicate whether this port is locked." 
        DEFVAL        	{ false }
        ::= { rcPortEntry 17 }

rcPortAutoNegotiationSupported OBJECT-TYPE
        SYNTAX        	TruthValue
        MAX-ACCESS        	read-only
        STATUS        	current
        DESCRIPTION   	"Indicate whether this port can support 
		      	auto-negotiation." 
        DEFVAL        	{ false }
        ::= { rcPortEntry 18 }

rcPortSingleRoutablePort OBJECT-TYPE
        SYNTAX        	TruthValue
        MAX-ACCESS        	read-only
        STATUS        	current
        DESCRIPTION   	"Indicate whether this port is a single routable
		      	port.  If this value is true, the port functions
			like a traditional router port."
        DEFVAL        	{ false }
        ::= { rcPortEntry 19 }

rcPortUnknownMacDiscard OBJECT-TYPE
        SYNTAX          TruthValue
        MAX-ACCESS      read-write
        STATUS          current
        DESCRIPTION     "If rcUnknownMacDiscard is set to True, 
                         then a packet with an unknown source MAC address
                         is dropped on that port, and other ports then
                         will discard any packets with this MAC address
                         in the destination field.  
                         For example, 
                         suppose 11:22:33:44:55:66 is an unknown source MAC,
                         packets with source MAC 11:22:33:44:55 coming from 
                         this port is discarded, further more, packets with
                         destination MAC 11:22:33:44:55:66 coming from
                         other ports are also discarded, unless this address
                         is later learned on another port or the restriction
                         ages out."

        DEFVAL          { false }
        ::= { rcPortEntry 20 }

rcPortNumStateTransition OBJECT-TYPE
        SYNTAX        	Counter32
        MAX-ACCESS        	read-only
        STATUS        	current
        DESCRIPTION   	"# state transitions."
        ::= { rcPortEntry 21 }

rcPortUserPriority OBJECT-TYPE
        SYNTAX  	INTEGER {
                            level0(0),
                            level1(1),
                            level2(2),
                            level3(3),
                            level4(4),
                            level5(5),
                            level6(6),
                            level7(7)
                        }
      	 MAX-ACCESS 	      	read-write
        STATUS 	      	deprecated
	       DESCRIPTION   	"User priority level."
        DEFVAL          { level7 }
	::= { rcPortEntry 22 }

rcPortAllowOversizeFrame OBJECT-TYPE
        SYNTAX          TruthValue
        MAX-ACCESS      read-write
        STATUS          deprecated
        DESCRIPTION     "Used to specify whether over-size frames should be
			processed or dropped."
        ::= { rcPortEntry 23 }

rcPortQosLevel OBJECT-TYPE
        SYNTAX  	INTEGER {
                            level0(0),
                            level1(1),
                            level2(2),
                            level3(3),
                            level4(4),
                            level5(5),
                            level6(6),
                            level7(7)
                        }
	       MAX-ACCESS 	      	read-write
        STATUS 	      	current
        DESCRIPTION     "Used to specify the Qos level packets, carried on this
                        port, should be processed with."
        DEFVAL          { level1 }
	::= { rcPortEntry 30 }

rcPortDiffServEnable OBJECT-TYPE
        SYNTAX        	TruthValue
        MAX-ACCESS        	read-write
        STATUS        	current
        DESCRIPTION   	"Used to enable/disable the Differentiated Service
			feature on this port."
        DEFVAL        	{ false }
        ::= { rcPortEntry 31 }

rcPortDiffServType OBJECT-TYPE
        SYNTAX  	INTEGER {
                            none(0),
                            access(1),
                            core(2)
                        }
	       MAX-ACCESS 	      	read-write
        STATUS 	      	current
	       DESCRIPTION   	"Used to specify the Differentiated Service type
			                   for this port."
        DEFVAL        	{ access }
	::= { rcPortEntry 32 }

rcPortDiffServIeee8021POverrideEnable OBJECT-TYPE
        SYNTAX        	TruthValue
        MAX-ACCESS        	read-write
        STATUS        	deprecated
	DESCRIPTION	"Used to enable/disable the Differentiated Service
			IEEE 802.1P over-ride feature."
        DEFVAL        	{ false }
        ::= { rcPortEntry 33 }

rcPortVendorDescr OBJECT-TYPE
        SYNTAX        	DisplayString (SIZE(16))
        MAX-ACCESS        	read-only
        STATUS        	current
        DESCRIPTION   	"Used to show the name of the vendor of this port's
			connector.  Only applicable to ports on a GBIC cards."
        ::= { rcPortEntry 34 }

rcPortName OBJECT-TYPE
        SYNTAX          DisplayString (SIZE (0..255))
        MAX-ACCESS      read-write
        STATUS          current
        DESCRIPTION     "This port's name."
        ::= { rcPortEntry 35 }

rcPortOctapidId OBJECT-TYPE
        SYNTAX        	Integer32
        MAX-ACCESS        	read-only
        STATUS        	deprecated
        DESCRIPTION   	"The octapid id of the mirrored port."
        ::= { rcPortEntry 36 }

rcPortWan OBJECT-TYPE
        SYNTAX          INTEGER {
		            none(0),  -- Not Applicable for non-10GE interface	
	                    wan(1),
			    lan(2)
	                }
        MAX-ACCESS      read-write
        STATUS          current
        DESCRIPTION     "Indicatie this port's current WAN/LAN mode. Valid for 10 GE only"
	       DEFVAL          { wan }
        ::= { rcPortEntry 37 }

rcPortTransport OBJECT-TYPE
        SYNTAX          INTEGER {
			    none(0),  -- N/A for non-10GE WAN interface	   	                   
			    sonet(1),
			    sdh(2)
	                }
        MAX-ACCESS      read-write
        STATUS          current
        DESCRIPTION     "Indicatie this port's current tranport layer. Valid for 10 GE only"
	       DEFVAL          { sonet }
        ::= { rcPortEntry 38 }
	
rcPortMultimediaFilterEnable OBJECT-TYPE
        SYNTAX          TruthValue
	       MAX-ACCESS      read-write
	       STATUS          current
	       DESCRIPTION     "Used to enable/disable the Telephony device selected on this port"
	       DEFVAL          { false }
	       ::= { rcPortEntry 39 }

rcPortMultimediaDevSelection OBJECT-TYPE
        SYNTAX          DisplayString 
	       MAX-ACCESS      read-write
	       STATUS          current
	       DESCRIPTION     "Used to set/get the selected Multimedia & 
                         Telephony Devices on this port. The String is 
                         the name of the device in the 
                         rcIpFilterMediaDevTable"
	       ::= { rcPortEntry 40 }

rcPortServiceType OBJECT-TYPE
        SYNTAX          INTEGER {
                            none  (0),
                            l2uni (1),
                            vpls   (2),
                            ip    (3),
                            serverl2uni (4)
                        }
        MAX-ACCESS      read-write
        STATUS          current
        DESCRIPTION     "Indicates the port functionality. 12uni is used to
                         configure the port to be part of Martini service,
                         tls is used to configure the port to be part of
                         Any2Any VPN service and ip is used to perform the IP
                         routing and mpls if enabled."
        ::= { rcPortEntry 41 }

rcPortMode OBJECT-TYPE
        SYNTAX          INTEGER {
                            none (0),
                            transparent (1),
                            switched (2)
                        }
        MAX-ACCESS      read-write
        STATUS          current
        DESCRIPTION     "The port mode for l2uni service type.If the port is
                         configured for l2uni service type, then the mode can
                         be transparent or switched."
        DEFVAL         { none }
        ::= { rcPortEntry 42 }

rcPortAdminRouting OBJECT-TYPE
        SYNTAX          EnableValue
        MAX-ACCESS      read-write
        STATUS          current
        DESCRIPTION     "Indicate whether the port is routable."
        DEFVAL          { enable }
   ::= { rcPortEntry 43 }

rcPortOperRouting OBJECT-TYPE
        SYNTAX          EnableValue
        MAX-ACCESS      read-only
        STATUS          current
        DESCRIPTION     "The status of the port whether is routable."
   ::= { rcPortEntry 44 }

rcPortPid OBJECT-TYPE
        SYNTAX          Integer32
        MAX-ACCESS      read-only
        STATUS          current
        DESCRIPTION     "The pid of the mirrored port."
        ::= { rcPortEntry 45 }

rcPortIeee8021POverrideEnable OBJECT-TYPE
      SYNTAX          TruthValue
      MAX-ACCESS      read-write
      STATUS          current
      DESCRIPTION     "Used to enable/disable IEEE 802.1P override.
                     If it is enabled, 802.1p vlaue from a tagged
                       frame may not honor."
      DEFVAL          { false }
      ::= { rcPortEntry 46 }

rcPortShaperEnable OBJECT-TYPE
      SYNTAX         TruthValue
      MAX-ACCESS     read-write
      STATUS         current
      DESCRIPTION   "Used to enable/disable shaper on the port."
      DEFVAL         { false }
      ::= { rcPortEntry 47 }

rcPortShaperMaxRate OBJECT-TYPE
      SYNTAX         Integer32 (1..10000)
      MAX-ACCESS     read-write
      STATUS         current
      DESCRIPTION   "Shaping rate in mega bits per second. Note that
                     actual shaping rate might be different from the
                     configured rate due to the rate granularity
                     of the shaper."
      DEFVAL         { 10 }
      ::= { rcPortEntry 48 }

rcPortShaperBurstSize OBJECT-TYPE
      SYNTAX        Integer32(4..16000)
      MAX-ACCESS    read-write
      STATUS        current
      DESCRIPTION   "Burst size in kilo bytes per second.  Note
                     that actual burst size might be different
                     from the configured size due to the granularity
                     of the shaper."
      DEFVAL          { 4 }
      ::= { rcPortEntry 49 }

rcPortCpLimitShutDown OBJECT-TYPE
        SYNTAX          TruthValue
        MAX-ACCESS      read-only
        STATUS          current
        DESCRIPTION     "A TRUE value indicates if CP Limit shut down 
                         the interface."
        ::= { rcPortEntry 50 }

rcPortHighSecureEnable OBJECT-TYPE
        SYNTAX          TruthValue
        MAX-ACCESS      read-write
        STATUS          current
        DESCRIPTION     "Enable/Disable high secure." 
        ::= { rcPortEntry 51 }

rcPortTlsPriorityOverride OBJECT-TYPE
        SYNTAX          EnableValue
        MAX-ACCESS      read-write
        STATUS          current
        DESCRIPTION     "Enable/Disable tls port priority override feature."
        DEFVAL          { disable }
        ::= { rcPortEntry 52 }

rcPortVctAbility OBJECT-TYPE
      SYNTAX        INTEGER {
                       vctNotCapable(1),
                       vctCapable(2)
                    }
      MAX-ACCESS    read-only
      STATUS        current
      DESCRIPTION   "If this object is TRUE, then the specified port is
                     hardware-capable of doing the VCT test, if the
                     rcPortAdminStatus is also true. If this object is
                     FALSE, then the hardware cannot do the VCT test
                     regardless of the setting of the rcPortAdminStatus."
        ::= { rcPortEntry 53 }

rcPortVctAdminStatus OBJECT-TYPE
      SYNTAX        EnableValue
      MAX-ACCESS    read-write
      STATUS        current
      DESCRIPTION   "Admin status for port VCT test. If this object is
                     set to TRUE, then the VCT test can be performed. If
                     it is set to FALSE, then the test cannot be performed,
                     even if the port hardware is capable of doing it. If
                     this variable si read, then the value returned is
                     what was previously written."
        ::= { rcPortEntry 54 }

rcPortMrouteStrLimit OBJECT-TYPE
        SYNTAX          Integer32 (1..32768)
        MAX-ACCESS      read-write
        STATUS          current
        DESCRIPTION     "maximum number of multicast streams that are
                         allowed to ingress to CPU through this port."
        DEFVAL          { 1984 }
        ::= { rcPortEntry 55 }

rcPortMrouteStrTimerCheck OBJECT-TYPE
        SYNTAX          Integer32 (1..3600)
        MAX-ACCESS      read-write
        STATUS          current
        DESCRIPTION     "sampling period to check number of multicast
                         streams that has ingressed CPU through this port."
        DEFVAL          { 10 }
        ::= { rcPortEntry 56 }

rcPortMrouteStrLimitEnable OBJECT-TYPE
        SYNTAX          TruthValue
        MAX-ACCESS      read-write
        STATUS          current
        DESCRIPTION     "enable or disable mroute stream limit on port."
        DEFVAL          { false }
        ::= { rcPortEntry 57 }

rcPortUpdateDynamicMacQosLevel OBJECT-TYPE
      SYNTAX        EnableValue
      MAX-ACCESS    read-write
      STATUS        current
      DESCRIPTION   "It is used to indicate whether to update qos
                     level for dynamic learned mac add resses
                     associated with a port-based vlan when port qos
                     level changes.  If it is set to TRUE, qos level
                     for all dynamic learned mac addresses will be
                     changed upon changing port qos level.  If it
                     is set to DISABLE, once a mac address is learned,
                     qos level will not updated when port qos level
                     changes."
      DEFVAL         { disable }
      ::= { rcPortEntry 58 }

rcPortVplsDualHoming    OBJECT-TYPE
        SYNTAX          INTEGER {
                            disable (0),
                            firstNNI (1),
                            secondNNI (2)
                        }
        MAX-ACCESS      read-write
        STATUS          current
        DESCRIPTION     "The VPLS dual homing is for VPLS service type only.
                         It can be disable, firstNNI or secondNNI."
        DEFVAL         { disable }
        ::= { rcPortEntry 59 }

rcPortVplsMgmtVlan      OBJECT-TYPE
        SYNTAX          TruthValue
        MAX-ACCESS      read-write
        STATUS          current
        DESCRIPTION     "Management Vlan is configured on this port"
        DEFVAL          { false }
        ::= { rcPortEntry 60 }

rcPortTlsManagedBySp  OBJECT-TYPE
        SYNTAX          TruthValue
        MAX-ACCESS      read-write
        STATUS          current
        DESCRIPTION     "True/False tls devices on port Managed By Service Provider."
	DEFVAL          { false }
        ::= { rcPortEntry 61 }

rcPortAutoNegAd OBJECT-TYPE
        SYNTAX          BITS {
                            advertise10Half(0),
                            advertise10Full(1),
                            advertise100Half(2),
                            advertise100Full(3),
                            advertise1000Half(4),
                            advertise1000Full(5),
                            advertiseMacPause(6),  -- Not supported in 8600
                            advertiseAsymPause(7), -- Not supported in 8600
			    advertiseNone(8)
                        }
        MAX-ACCESS      read-write
        STATUS          current
        DESCRIPTION     "This object is used to specify the port speed
                         and duplex abilities to be advertised during
                         link negotiation.

                         bit 0 - 10 half duplex advertised
                         bit 1 - 10 full duplex advertised
                         bit 2 - 100 half duplex advertised
                         bit 3 - 100 full duplex advertised
                         bit 4 - 1000 half duplex advertised
                         bit 5 - 1000 full duplex advertised
                         bit 6 - Mac PAUSE frame support advertised
                         bit 7 - Asymmetric PAUSE frame support advertised
			 bit 8 - No advertisements

                         The abilities specified in this object are only used
                         when auto-negotiation is enabled on the port.  If all
                         bits in this object are disabled, and auto-negotiation
                         is enabled on the port, then the physical link process
                         on the port will be disabled (if hardware supports 
                         this ability).

                         Any change in the value of this bit map will force the
                         PHY to restart the auto-negotiation process.  This will
                         have the same effect as physically unplugging and
                         reattaching the cable plant attached to this port.

                         The capabilities being advertised are either all the 
	                 capabilities supported by the hardware or the user- 
		   	 configured capabilities which is a subset of all the 
		         capability supported by hardware.
          
                   	 The default value for this object will be all the 
		         capabilities supported by the hardware.

		         Note that bit 6 and bit 7 are currently not supported
		         in ERS8600."
        ::= { rcPortEntry 62 }

rcPortAutoNegAdCapability OBJECT-TYPE
        SYNTAX          BITS {
                            advertise10Half(0),
                            advertise10Full(1),
                            advertise100Half(2),
                            advertise100Full(3),
                            advertise1000Half(4),
                            advertise1000Full(5),
                            advertiseMacPause(6),
                            advertiseAsymPause(7)
                        }
        MAX-ACCESS      read-only
        STATUS          current
        DESCRIPTION     "This object indicates the port speed and duplex
                         capabilities that hardware can actually support on a
                         port, and which may be advertised by the port
                         using auto-negotiation. Bit 7 tells if a port supports
                         pause frame capabilities (for full-duplex links) as a
                         part of the advertisement.

                         bit 0 - 10 half duplex advertisements
                         bit 1 - 10 full duplex advertisements
                         bit 2 - 100 half duplex advertisements
                         bit 3 - 100 full duplex advertisements
                         bit 4 - 1000 half duplex advertisements
                         bit 5 - 1000 full duplex advertisements
                         bit 6 - Mac PAUSE frame support advertisements
                         bit 7 - Asymmetric PAUSE frame support advertisements

                         If auto negotiation is not supported by the port
                         hardware, then all bits will reflect a value of zero."
        ::= { rcPortEntry 63 }

rcPortAutoRecoverPort OBJECT-TYPE
        SYNTAX          TruthValue
        MAX-ACCESS      read-write
        STATUS          current
        DESCRIPTION     "enable or disable auto recovery of port from action
                         taken by cp-limit, link flap or loop detect features"
        DEFVAL          { false }
        ::= { rcPortEntry 64 }

rcPortExtCplimitConf OBJECT-TYPE
        SYNTAX        INTEGER {
                         none(1),
                         softDown(2),
                         hardDown(3)
                      }        
        MAX-ACCESS    read-write
        STATUS        current
        DESCRIPTION   "Indicates the port configuration for extended CP-LIMIT"
        DEFVAL        { none}
        ::= { rcPortEntry 65 }

rcPortExtCplimitUtilRate OBJECT-TYPE
        SYNTAX        Integer32 (1..100)
        MAX-ACCESS    read-write
        STATUS        current
        DESCRIPTION   "Threshold for Ingress traffic utilization rate of the port
                      for extended CP-LIMIT"
        DEFVAL        { 50 }
        ::= { rcPortEntry 66 }

rcPortEgressRateLimit OBJECT-TYPE
        SYNTAX          Integer32(0 | 64..10000000)
        MAX-ACCESS      read-write
        STATUS          current
        DESCRIPTION     "Egress Rate Limit. 0 means disabled."
        ::= { rcPortEntry 67 }

rcPortEgressRateLimitState OBJECT-TYPE
        SYNTAX        EnableValue
        MAX-ACCESS    read-write
        STATUS        current
        DESCRIPTION   "Used to enable/disable shape/egress-rate-limit 
		       functionality."
        DEFVAL          { disable }
        ::= { rcPortEntry 68 }

rcPortBpduFilteringTimerCount OBJECT-TYPE
        SYNTAX        TimeInterval (0..6553500)
        MAX-ACCESS    read-only
        STATUS        current
        DESCRIPTION   "The remaining time the port will be disabled due
                       to a BPDU received when BPDU filtering is enabled."
        ::= { rcPortEntry 69 }

rcPortBpduFilteringTimeout OBJECT-TYPE
        SYNTAX        TimeInterval (0..6553500)
        MAX-ACCESS    read-write
        STATUS        current
        DESCRIPTION   "The time the port will be disabled when a BPDU is
                       received when BPDU filtering is enabled."
        ::= { rcPortEntry 70 }

rcPortBpduFilteringAdminEnabled OBJECT-TYPE
        SYNTAX        TruthValue
        MAX-ACCESS    read-write
        STATUS        current
        DESCRIPTION   "Used to enable/disable BPDU filtering."
        DEFVAL          { false }
        ::= { rcPortEntry 71 }

rcPortBpduFilteringOperEnabled OBJECT-TYPE
        SYNTAX        TruthValue
        MAX-ACCESS    read-only
        STATUS        current
        DESCRIPTION   "Indicates whether BPDU filtering is actually
                       enabled or disabled."
        ::= { rcPortEntry 72 }

rcPortQinqEtherType   OBJECT-TYPE
        SYNTAX        Integer32 (1..'FFFF'h) 
        MAX-ACCESS    read-write
        STATUS        current
        DESCRIPTION   "The qinq ether type value. It is hex value. 
                       It should be displayed and input as Hex value. It is 
		       only be used when port is associated with QnQ service 
		       UNI. Otherwise, it would be ignored"
        DEFVAL        { '8020'h }
        ::= { rcPortEntry 73 }

rcPortTrustDscp OBJECT-TYPE
      SYNTAX        TruthValue
      MAX-ACCESS    read-write
      STATUS        current
      DESCRIPTION   "Used to enable/disable the trusted DSCP feature.
                     If enabled, the internal qos-level and 802.1p value are derived
                     from the received packet's DSCP value.  This MIB object is
                     applicable to ports in 8348GTX so that higher priority IP traffic
                     can bypass the oversubscribed cascading link."
      DEFVAL        {false}
      ::= {rcPortEntry 74}

rcPortCpLimitEnable OBJECT-TYPE
        SYNTAX      EnableValue
        MAX-ACCESS  read-write
        STATUS      current
        DESCRIPTION "Used to enable/disable the control packet rate limit.
                     Specifies whether or not rate limiting is currently in
                     operation for multicast and broadcast packets for the
                     specified port. "
        DEFVAL      { enable }
        ::= {rcPortEntry 75 }

rcPortCpMulticastLimit OBJECT-TYPE
        SYNTAX      Integer32(1000..100000)
        MAX-ACCESS  read-write
        STATUS      current
        DESCRIPTION "Used to limit Multicast traffic on the specified port. Sets
                    the limit in packets per second."
        DEFVAL      { 10000 }
        ::= { rcPortEntry 76 }

rcPortCpBroadcastLimit OBJECT-TYPE
        SYNTAX      Integer32(1000..100000)
        MAX-ACCESS  read-write
        STATUS      current
        DESCRIPTION "Used to limit Broadcast traffic on the specified port. Sets
                     the limit in packets per second. "
        DEFVAL      { 10000 }
        ::= { rcPortEntry 77 }

rcPortSmartAutoNegotiate OBJECT-TYPE
        SYNTAX      TruthValue
        MAX-ACCESS  read-write
        STATUS      current
        DESCRIPTION "This object indicates whether 'smart' autonegotiation is
                     enabled on a port (smart autonegotiation indicates that the
                     port can sense whether its partner has autonegotiation
                     enabled).  This object, when supported, works in conjunction
                     with rcPortAutoNegotiate.  It is an inconsistentValue error
                     to set rcPortAutoNegotiate to false(2) and this object to
                     true(1) in the same Set request.  Setting the object to
                     true(1) will automatically change rcPortAutoNegotiate to
                     true(1).  Similarly, setting rcPortAutoNegotiate to false(2)
                     will automatically change this object to false(2)."
        DEFVAL      { false }
        ::= { rcPortEntry 78 }

rcPortMepList OBJECT-TYPE
        SYNTAX        OCTET STRING (SIZE (0..408))
        MAX-ACCESS    read-write
        STATUS        current
        DESCRIPTION   "List of Meps assigned to this entry. 
		       A mep is consist of <md>.<ma>.<mep_id>. Domain
		       Name, Association and Mep Id is separated by '.' 
		       A list of mep is consist of 
		       <md1>.<ma1>.<mepid1>,<md2>.<ma2>.<mepid2>,... 
		       Each mep is separated by ','. Maximum up 8 meps"
        ::= { rcPortEntry 79 }

rcPortNumOfMep OBJECT-TYPE
        SYNTAX        	Integer32(0..8)
        MAX-ACCESS      read-only
        STATUS        	current
        DESCRIPTION   	"Used to indicate the number of Meps
                      	is assigned to this entry"
        ::= { rcPortEntry 80 }

rcPortAdacStatus OBJECT-TYPE
      SYNTAX        TruthValue
      MAX-ACCESS    read-write
      STATUS        current
      DESCRIPTION   "If enabled, the Nortel IP phones connected to the port will be
                     configured in the voice VLAN."
      ::= { rcPortEntry 81 }

rcPortPvid OBJECT-TYPE
        SYNTAX        Integer32 (0..4093)
        MAX-ACCESS    read-write
        STATUS        current
        DESCRIPTION   "A port Vlan Id associates with ESM and RModule 
	               port for OEL2/MIM traffic"
	 DEFVAL        { 0 }	   
        ::= { rcPortEntry 82 }

rcPortTdp  OBJECT-TYPE
        SYNTAX          EnableValue
        MAX-ACCESS      read-write
        STATUS          current
        DESCRIPTION     "This attribute allows to Enable/Disable Transparent
                         Domain Protocol at the port level on the ESM and 
                         Power Ranger Card. For the TDP packet to go out on
                         the port, topology should be enabled both at the port 
                         and box level also."
        DEFVAL          { disable }
        ::= { rcPortEntry 83 }

rcPortClockSource OBJECT-TYPE
        SYNTAX          INTEGER {
                            none (0),
                            line (1),
                            internal (2)
                        }
        MAX-ACCESS      read-write
        STATUS          current
        DESCRIPTION     "Indicates this port's current WAN clock source.
                         Valid for 10 GE WAN only"
        DEFVAL          { internal }
        ::= { rcPortEntry 84 }

rcPortIngressRateLimit OBJECT-TYPE
        SYNTAX          Integer32(1000..10000000)
        MAX-ACCESS      read-write
        STATUS          current
        DESCRIPTION     "Limits the amount of traffic from this Ingress port."
        ::= { rcPortEntry 85 }

rcPortIngressRateLimitState OBJECT-TYPE
        SYNTAX          EnableValue
        MAX-ACCESS      read-write
        STATUS          current
        DESCRIPTION     "Used to enable/disable police/ingress-rate-limit
                         functionality."
        DEFVAL          { disable }
        ::= { rcPortEntry 86 }

rcPortVrfIdList OBJECT-TYPE
        SYNTAX          IdList (SIZE (0..512))
        MAX-ACCESS      read-only
        STATUS          current
        DESCRIPTION     "The set of VRF ids to which this port belongs."
        ::= { rcPortEntry 87 }
 
rcPortCfmVid OBJECT-TYPE
        SYNTAX        Integer32 (0..4095)
        MAX-ACCESS    read-write
        STATUS        current
        DESCRIPTION   "CFM default port vid"
	DEFVAL        { 0 }	   
        ::= { rcPortEntry 88 }

rcPortUserLabel1  OBJECT-TYPE
 	SYNTAX   	DisplayString (SIZE(0..89))
        MAX-ACCESS      read-write
        STATUS          current
        DESCRIPTION     "User provided field. Used to give extra management information/data "
        ::= { rcPortEntry 89 }

rcPortUserLabel2  OBJECT-TYPE
	SYNTAX 		DisplayString (SIZE(0..89))
        MAX-ACCESS      read-write
        STATUS          current
        DESCRIPTION     "User provided additional field. Used to give extra management information/data "
        ::= { rcPortEntry 90 }

rcPortClearCfmStats   OBJECT-TYPE
        SYNTAX          TruthValue
        MAX-ACCESS      read-write
        STATUS          current
        DESCRIPTION     "To clear the port counter"
        DEFVAL          { false }
        ::= { rcPortEntry 91 }

rcPortInterfaceType OBJECT-TYPE
        SYNTAX INTEGER {
                        normal(1),
                        silent(2),
                        uni(3) 
                        } 
        MAX-ACCESS      read-write
        STATUS          current
        DESCRIPTION     "This value indicates whether a port is of type <normal/si
                         lent/uni>. A port can be included in any EVPN service 
                         only if this attribute is set to uni. If the port is not
			part of any VLAN the interface-type is set to silent. 
			Before adding a port to a VLAN the interface type should 
			be changed to normal."
        DEFVAL          { silent }
        ::= { rcPortEntry 92 }

rcPortCfmControlMep OBJECT-TYPE
        SYNTAX        DisplayString (SIZE(0..57))
        MAX-ACCESS    read-write
        STATUS        current
        DESCRIPTION   "MEP assigned for CFM Control.
                       A mep consists of <md>.<ma>.<mep_id>. Domain
                       Name, Association and Mep Id is separated by '.'"
        ::= { rcPortEntry 93 }

rcPortMtu OBJECT-TYPE
        SYNTAX        Integer32 (1518..9600)
        MAX-ACCESS    read-write
        STATUS        current
        DESCRIPTION   "Port Mtu"
	DEFVAL        { 1518 }	   
        ::= { rcPortEntry 94 }

rcPortMtuState          OBJECT-TYPE
        SYNTAX          EnableValue
        MAX-ACCESS      read-write
        STATUS          current
        DESCRIPTION     "Used to enable/disable Port Mtu
                         functionality."
        DEFVAL          { disable }
        ::= { rcPortEntry 95 }

rcPortVrfNameList OBJECT-TYPE
        SYNTAX          OCTET STRING
        MAX-ACCESS      read-only
        STATUS          current
        DESCRIPTION     "The set of VRF names to which this port belongs."
        ::= { rcPortEntry 96 }

rcPortBrouterVrfId OBJECT-TYPE
        SYNTAX          VrfIdentifier
        MAX-ACCESS      read-write
        STATUS          current
        DESCRIPTION     "Gives the VRF Id for this Brouter port. "
        ::= { rcPortEntry 97 }

rcPortBrouterVrfName OBJECT-TYPE
        SYNTAX          DisplayString (SIZE(0..64))
        MAX-ACCESS      read-only
        STATUS          current
        DESCRIPTION     "Gives the VRF Name for this Brouter port. "
        ::= { rcPortEntry 98 }

rcPortVrfCount OBJECT-TYPE
        SYNTAX          Counter32
        MAX-ACCESS      read-only
        STATUS          current
        DESCRIPTION     "The total number of VRFs this port is associated to."
        ::= { rcPortEntry 99 }

rcPortCtrlPktDropLimitEnable OBJECT-TYPE
        SYNTAX          EnableValue
        MAX-ACCESS      read-write
        STATUS          current
        DESCRIPTION     "Used to enable/disable Control Packets Drop
                        Rate Limiter functionality."
        DEFVAL          { disable }
        ::= { rcPortEntry 100 }

rcPortCtrlPktDropLimit  OBJECT-TYPE
        SYNTAX          Integer32(0 | 20..1000)
        MAX-ACCESS      read-write
        STATUS          current
        DESCRIPTION     "Indicates the Control Packet drop rate limit
                        value"
        DEFVAL          { 20 }
        ::= { rcPortEntry 101 }

rcPortCtrlPktShutdownLimitEnable OBJECT-TYPE
        SYNTAX          EnableValue
        MAX-ACCESS      read-write
        STATUS          current
        DESCRIPTION     "Used to enable/disable Control Packets
                        Shutdown Rate Limiter functionality."
        DEFVAL          { disable }
        ::= { rcPortEntry 102 }

rcPortCtrlPktShutdownLimit  OBJECT-TYPE
        SYNTAX          Integer32(0 | 20..1000)
        MAX-ACCESS      read-write
        STATUS          current
        DESCRIPTION     "Indicates the Control Packet shutdown rate
                        Limit value"
        DEFVAL          { 100 }
        ::= { rcPortEntry 103 }

rcPortCtrlPktShutdownRtExceeded  OBJECT-TYPE
        SYNTAX          TruthValue
        MAX-ACCESS      read-write
        STATUS          current
        DESCRIPTION     "Indicates if the Shutdown rate has been exceeded
                         on the port"
        DEFVAL        { false }
        ::= { rcPortEntry 104 } 

rcPortCtrlPktDropRtExceeded  OBJECT-TYPE
        SYNTAX          TruthValue
        MAX-ACCESS      read-write
        STATUS          current
        DESCRIPTION     "Indicates if the Drop rate has been exceeded
                         on the port"
        DEFVAL        { false }
        ::= { rcPortEntry 105 }

rcPortDhcpOption82SubscriberId  OBJECT-TYPE
        SYNTAX          DisplayString
        MAX-ACCESS      read-write
        STATUS          current
        DESCRIPTION
         "This object contains the DHCP option 82 subscriber ID string to
         be used in sub-option 6.  If the value is an empty string, then
         sub-option 6 is not included in option 82"
        DEFVAL        { ''h }
        ::= { rcPortEntry 106 }

rcPortServiceCardType  OBJECT-TYPE
        SYNTAX        INTEGER {
                         esm8x1000Base(1),
                         pr48x1000BaseTX(2),
                         pr30x1000BaseSXBB(3),
                         pr3x10GBaseGbic(4),
                         pr3x10GBaseXZW(5),
                         prPR48x1000BaseGBRS(6),
                         prPR48x1000BaseGTRS(7),
                         prPR12X10GBaseXLRS(8),
                         prPR34xXGRS(9),
                         prPR48x1000BaseGXRS(10),
                         prPR30x1000BaseGBRS(11),
                         prPR6X10GBaseXLRS(12),
                         prPR26xXGRS(13),
                         other(14)
                      }
        MAX-ACCESS    read-only
        STATUS        current
        DESCRIPTION   "Port Hardware type, which includes PowerRanger,
                      ESM port and other"
        ::= { rcPortEntry 107}

rcPortIngressRatePeak OBJECT-TYPE
        SYNTAX           INTEGER(0 | 64..10000000)
        MAX-ACCESS       read-write
        STATUS           current
        DESCRIPTION     "Peak rate limit for this port. 0 means disable."
        DEFVAL           { 0 }
        ::= { rcPortEntry 108 }

rcPortIngressRateSvc OBJECT-TYPE
        SYNTAX           INTEGER(0 | 64..10000000)
        MAX-ACCESS       read-write
        STATUS           current
        DESCRIPTION     "Service rate limit for this port. 0 means disable."
        DEFVAL           { 0 }
        ::= { rcPortEntry 109 }

rcPortCpLimitPktRate  OBJECT-TYPE
        SYNTAX          INTEGER(1000..20000)
        MAX-ACCESS      read-write
        STATUS          current
        DESCRIPTION     "Used to limit Control packets on the
                         port to qos-levels 6 and 7.
                         Sets the limit in packets per second."
        DEFVAL          { 8000 }
        ::= { rcPortEntry 110 }

rcPortCpLimitShutDownEnable  OBJECT-TYPE
        SYNTAX          TruthValue
        MAX-ACCESS      read-write
        STATUS          current
        DESCRIPTION     "Used to indicate if the port should be shutdown
                         when the CpLimitPktRate is exceeded."
        DEFVAL          { false }
        ::= { rcPortEntry 111 }

rcPortRmonEnable OBJECT-TYPE
        SYNTAX      	TruthValue
        MAX-ACCESS  	read-write
        STATUS      	current
        DESCRIPTION 	"Used to set Remote Monitoring enable/disable"
        DEFVAL          { false }
        ::= { rcPortEntry 112 }
 
rcPortIpsecEnable OBJECT-TYPE
        SYNTAX      	TruthValue
        MAX-ACCESS  	read-write
        STATUS      	current
        DESCRIPTION 	"Used to set IPSEC enable/disable"
        DEFVAL          { false }
        ::= { rcPortEntry 113 }


-- Port Pcap Table

rcPortPcapTable OBJECT-TYPE
        SYNTAX        SEQUENCE OF RcPortPcapEntry
        MAX-ACCESS    not-accessible
        STATUS        current
        DESCRIPTION   "Port pcap Table"
        ::= { rcPort 2 }

rcPortPcapEntry OBJECT-TYPE
        SYNTAX        RcPortPcapEntry
        MAX-ACCESS    not-accessible
        STATUS        current
        DESCRIPTION   "Entry containing pcap info. for a particular port"
        INDEX         { rcPortPcapIndex }
        ::= { rcPortPcapTable 1 }

RcPortPcapEntry ::= SEQUENCE {
        rcPortPcapIndex            InterfaceIndex,
        rcPortPcapEnable           TruthValue,
        rcPortPcapMode             INTEGER,
        rcPortPcapFilterListSize   Integer32,
        rcPortPcapFilterList       OCTET STRING,
        rcPortPcapAclFilterListSize Integer32,
        rcPortPcapAclFilterList    OCTET STRING
        }


rcPortPcapIndex OBJECT-TYPE
        SYNTAX          InterfaceIndex
        MAX-ACCESS      read-only
        STATUS          current
        DESCRIPTION     "An index value that uniquely identifies a port.
                         This value is similar to ifIndex in MIB2."
        ::= { rcPortPcapEntry 1 }

rcPortPcapEnable OBJECT-TYPE
        SYNTAX          TruthValue
        MAX-ACCESS      read-write
        STATUS          current
        DESCRIPTION     "To enable pcap for the port"
        DEFVAL          { false }
        ::= { rcPortPcapEntry 2 }

rcPortPcapMode OBJECT-TYPE
        SYNTAX          INTEGER {
                                tx(1),
                                rx(2),
                                both(3),
                                rxFilter(4),
	          txFilter(5),
                               bothFilter(6)
                        }
        MAX-ACCESS      read-write
        STATUS          current
        DESCRIPTION     "Mode in which pcap is enabled"
        DEFVAL          { rx }
        ::= { rcPortPcapEntry 3 }

rcPortPcapFilterListSize OBJECT-TYPE
        SYNTAX          Integer32 (0..128)
        MAX-ACCESS      read-only
        STATUS          current
        DESCRIPTION     "Used to indicate the number of filter list(s)
                         that are assigned to this port."
        ::= { rcPortPcapEntry 4 }


rcPortPcapFilterList OBJECT-TYPE
        SYNTAX          OCTET STRING (SIZE(0..256))
        MAX-ACCESS      read-write
        STATUS          current
        DESCRIPTION     "Used to indicate zero or more filter lists that
                         are associated with this port for pcap.  Each
                         filter list identifier is stored as two bytes
                         in this array starting from offset zero.  Any
                         unused bytes should be set to zero."
        ::= { rcPortPcapEntry 5 }

rcPortPcapAclFilterListSize OBJECT-TYPE
        SYNTAX          Integer32 (0..128)
        MAX-ACCESS      read-only
        STATUS          current    
        DESCRIPTION     "Used to indicate the number of ACL filter(s)
                         that are assigned to this port which has mirror set
                         as global-action."
        ::= { rcPortPcapEntry 6 }

rcPortPcapAclFilterList OBJECT-TYPE
        SYNTAX          OCTET STRING (SIZE(0..256))
        MAX-ACCESS      read-write
        STATUS          current
        DESCRIPTION     "Used to indicate zero or more ACL filter lists
                         that are associated with this port for pcap (has mirror
                         set as global-action).  Each ACL filter list
                         identifier is stored as two bytes
                         in this array starting from offset zero.  Any
                         unused bytes should be set to zero."
        ::= { rcPortPcapEntry 7 }

-- rcPortPoe IfIndex to Pse Index Table

rcPortPoe OBJECT IDENTIFIER ::= { rcPort 3 }

rcPortPoePseIndexTable OBJECT-TYPE
        SYNTAX        SEQUENCE OF RcPortPoePseIndexEntry
        MAX-ACCESS    not-accessible
        STATUS        current
        DESCRIPTION   "Port table"
        ::= { rcPortPoe 1 }

rcPortPoePseIndexEntry OBJECT-TYPE
        SYNTAX        RcPortPoePseIndexEntry
        MAX-ACCESS    not-accessible
        STATUS        current
        DESCRIPTION   "Entry containing info. for a particular port"
        INDEX         { rcPortPoePseIndexIfIndex }
        ::= { rcPortPoePseIndexTable 1 }

RcPortPoePseIndexEntry ::= SEQUENCE {
      rcPortPoePseIndexIfIndex                 InterfaceIndex,
      rcPortPoePseIndexGroupIndex              Integer32,
      rcPortPoePseIndexPortIndex               Integer32

}

rcPortPoePseIndexIfIndex OBJECT-TYPE
     SYNTAX      InterfaceIndex
     MAX-ACCESS  read-only
     STATUS      current
     DESCRIPTION "An index value that uniquely identifies an interface
                  to a PSE port device.  The interface identified by a
                  particular value of this index is the same interface
                  as identified by the same value of ifIndex."
     ::= { rcPortPoePseIndexEntry 1 }

rcPortPoePseIndexGroupIndex OBJECT-TYPE
     SYNTAX      Integer32 (0..65535)
     MAX-ACCESS  read-only
     STATUS      current
     DESCRIPTION "An index value that uniquely identifies the group
                  containing the port to which a power Etherenet PSE
                  is connected. Group means box in the stack, module
                  in a rack and the value 1 MUST be used for
                  non-modular devices."
     ::= { rcPortPoePseIndexEntry 2 }

rcPortPoePseIndexPortIndex OBJECT-TYPE
     SYNTAX      Integer32 (0..65535)
     MAX-ACCESS  read-only
     STATUS      current
     DESCRIPTION "This variable uniquely identifies the power Ethernet
                  PSE port within group rcPoePseGroupIndex to which the
                  power Ethernet PSE entry is connected."
     ::= { rcPortPoePseIndexEntry 3 }


-- POE main Pse extn table

rcPortPoeMainPseExtnTable OBJECT-TYPE
        SYNTAX        SEQUENCE OF RcPortPoeMainPseExtnEntry
        MAX-ACCESS    not-accessible
        STATUS        current
        DESCRIPTION   "Port table"
        ::= { rcPortPoe 2 }

rcPortPoeMainPseExtnEntry OBJECT-TYPE
        SYNTAX        RcPortPoeMainPseExtnEntry
        MAX-ACCESS    not-accessible
        STATUS        current
        DESCRIPTION   "Entry containing info. for a particular port"
        INDEX         { rcPortPoeMainPseExtnGroupIndex }
        ::= { rcPortPoeMainPseExtnTable 1 }

RcPortPoeMainPseExtnEntry ::= SEQUENCE {
      rcPortPoeMainPseExtnGroupIndex              Integer32,
      rcPortPoeMainPseExtnPwrAdmin                EnableValue,
      rcPortPoeMainPseExtnPwrPriority             INTEGER,
      rcPortPoeMainPseExtnDeviceDetectType        INTEGER,
      rcPortPoeMainPseExtnPwrLimit                Integer32
}

rcPortPoeMainPseExtnGroupIndex OBJECT-TYPE
     SYNTAX      Integer32 (0..65535)
     MAX-ACCESS  read-only
     STATUS      current
     DESCRIPTION "An index value that uniquely identifies an interface
                  to a PSE port device.  The interface identified by a
                  particular value of this index is the same interface
                  as identified by the same value of ifIndex."
     ::= { rcPortPoeMainPseExtnEntry 1 }

rcPortPoeMainPseExtnPwrAdmin OBJECT-TYPE
     SYNTAX      EnableValue
     MAX-ACCESS  read-write
     STATUS      current
     DESCRIPTION "An index value that uniquely identifies the group
                  containing the port to which a power Etherenet PSE
                  is connected. Group means box in the stack, module
                  in a rack and the value 1 MUST be used for
                  as identified by the same value of ifIndex."
     DEFVAL      { disable }
     ::= { rcPortPoeMainPseExtnEntry 2 }

rcPortPoeMainPseExtnPwrPriority OBJECT-TYPE
     SYNTAX      INTEGER {
                    critical(1),
                    high(2),
                    low(3)
                 }
     MAX-ACCESS  read-write
     STATUS      current
     DESCRIPTION "An index value that uniquely identifies the group
                  containing the port to which a power Etherenet PSE
                  is connected. Group means box in the stack, module
                  in a rack and the value 1 MUST be used for
                  as identified by the same value of ifIndex."
     DEFVAL      { low }
     ::= { rcPortPoeMainPseExtnEntry 3 }

rcPortPoeMainPseExtnDeviceDetectType OBJECT-TYPE
     SYNTAX      INTEGER {
                    p802dot3af(1),
                    p802dot3afAndLegacy(2)
                 }
     MAX-ACCESS  read-write
     STATUS      current
     DESCRIPTION "An index value that uniquely identifies the group
                  containing the port to which a power Etherenet PSE
                  is connected. Group means box in the stack, module
                  in a rack and the value 1 MUST be used for
                  as identified by the same value of ifIndex."
     DEFVAL      { p802dot3afAndLegacy }
     ::= { rcPortPoeMainPseExtnEntry 4 }

rcPortPoeMainPseExtnPwrLimit OBJECT-TYPE
     SYNTAX      Integer32 (37..800)
     MAX-ACCESS  read-write
     STATUS      current
     DESCRIPTION "The maximum available PoE power of the main PSE 
                  expressed in Watts."
     DEFVAL      { 200 }
     ::= { rcPortPoeMainPseExtnEntry 5 }

-- POE Pse Port extn table

rcPortPoePsePortExtnTable OBJECT-TYPE
        SYNTAX        SEQUENCE OF RcPortPoePsePortExtnEntry
        MAX-ACCESS    not-accessible
        STATUS        current
        DESCRIPTION   "Port table"
        ::= { rcPortPoe 3 }

rcPortPoePsePortExtnEntry OBJECT-TYPE
        SYNTAX        RcPortPoePsePortExtnEntry
        MAX-ACCESS    not-accessible
        STATUS        current
        DESCRIPTION   "Entry containing info. for a particular port"
        INDEX         { rcPortPoePsePortExtnGroupIndex,
                        rcPortPoePsePortExtnPortIndex }
        ::= { rcPortPoePsePortExtnTable 1 }

RcPortPoePsePortExtnEntry ::= SEQUENCE {
      rcPortPoePsePortExtnGroupIndex              Integer32,
      rcPortPoePsePortExtnPortIndex               Integer32,
      rcPortPoePsePortExtnPwrLimit                Integer32,
      rcPortPoePsePortExtnMeasuredVolt            Integer32,
      rcPortPoePsePortExtnMeasuredCurrent         Integer32,
      rcPortPoePsePortExtnPwrConsumpt             Integer32

}

rcPortPoePsePortExtnGroupIndex OBJECT-TYPE
     SYNTAX      Integer32 (1..2147483647)
     MAX-ACCESS  read-only
     STATUS      current
     DESCRIPTION "An index value that uniquely identifies an interface
                  to a PSE port device.  The interface identified by a
                  particular value of this index is the same interface
                  as identified by the same value of ifIndex."
     ::= { rcPortPoePsePortExtnEntry 1 }

rcPortPoePsePortExtnPortIndex OBJECT-TYPE
     SYNTAX      Integer32 (1..2147483647)
     MAX-ACCESS  read-only
     STATUS      current
     DESCRIPTION "An index value that uniquely identifies an interface
                  to a PSE port device.  The interface identified by a
                  particular value of this index is the same interface
                  as identified by the same value of ifIndex."
     ::= { rcPortPoePsePortExtnEntry 2 }

rcPortPoePsePortExtnPwrLimit OBJECT-TYPE
     SYNTAX      Integer32 (3..16)
     MAX-ACCESS  read-write
     STATUS      current
     DESCRIPTION "An index value that uniquely identifies the group
                  containing the port to which a power Etherenet PSE
                  is connected. Group means box in the stack, module
                  in a rack and the value 1 MUST be used for
                  as identified by the same value of ifIndex."
     DEFVAL      { 16 }
     ::= { rcPortPoePsePortExtnEntry 3 }

rcPortPoePsePortExtnMeasuredVolt OBJECT-TYPE
     SYNTAX      Integer32
     MAX-ACCESS  read-only
     STATUS      current
     DESCRIPTION "An index value that uniquely identifies the group
                  containing the port to which a power Etherenet PSE
                  is connected. Group means box in the stack, module
                  in a rack and the value 1 MUST be used for
                  as identified by the same value of ifIndex."
     ::= { rcPortPoePsePortExtnEntry 4 }

rcPortPoePsePortExtnMeasuredCurrent OBJECT-TYPE
     SYNTAX      Integer32
     MAX-ACCESS  read-only
     STATUS      current
     DESCRIPTION "An index value that uniquely identifies the group
                  containing the port to which a power Etherenet PSE
                  is connected. Group means box in the stack, module
                  in a rack and the value 1 MUST be used for
                  as identified by the same value of ifIndex."
     ::= { rcPortPoePsePortExtnEntry 5 }

rcPortPoePsePortExtnPwrConsumpt OBJECT-TYPE
     SYNTAX      Integer32
     MAX-ACCESS  read-only
     STATUS      current
     DESCRIPTION "An index value that uniquely identifies the group
                  containing the port to which a power Etherenet PSE
                  is connected. Group means box in the stack, module
                  in a rack and the value 1 MUST be used for
                  as identified by the same value of ifIndex."
     ::= { rcPortPoePsePortExtnEntry 6 }



-- PORT LACP 

rcPortLacpTable OBJECT-TYPE
        SYNTAX        SEQUENCE OF RcPortLacpEntry
        MAX-ACCESS    not-accessible
        STATUS        current
        DESCRIPTION   "Port LACP table"
        ::= { rcPort 4 }

rcPortLacpEntry OBJECT-TYPE
        SYNTAX        RcPortLacpEntry
        MAX-ACCESS    not-accessible
        STATUS        current
        DESCRIPTION   "Entry containing info. for a particular port"
        INDEX         { rcPortIndex }
        ::= { rcPortLacpTable 1 }

RcPortLacpEntry ::= SEQUENCE {
    rcPortLacpAdminEnable                 TruthValue,
    rcPortLacpOperEnable                  TruthValue,
    rcPortLacpFastPeriodicTime            Integer32,
    rcPortLacpSlowPeriodicTime            Integer32,
    rcPortLacpTimeoutScale                Integer32,
    rcPortLacpAggrWaitTime                Integer32,
    rcPortLacpFastPeriodicTimeOper   Integer32,
    rcPortLacpSlowPeriodicTimeOper   Integer32,
    rcPortLacpTimeoutScaleOper   Integer32,
    rcPortLacpAggrWaitTimeOper   Integer32
    }

rcPortLacpAdminEnable OBJECT-TYPE
        SYNTAX        TruthValue
        MAX-ACCESS    read-write
        STATUS        current
        DESCRIPTION   "Administratively enable/disable LACP on a port"
        DEFVAL        { false }
        ::= { rcPortLacpEntry 1 }

rcPortLacpOperEnable OBJECT-TYPE
        SYNTAX        TruthValue
        MAX-ACCESS    read-only
        STATUS        current
        DESCRIPTION   "Indicates if LACP is operationally enabled or disabled 
                       on a port"
        ::= { rcPortLacpEntry 2 }

rcPortLacpFastPeriodicTime OBJECT-TYPE
        SYNTAX        Integer32 (200..20000)
        MAX-ACCESS    read-write
        STATUS        current
        DESCRIPTION   "The number of miliseconds between periodic transmissions
                       using Short Timeouts."
        DEFVAL        { 1000 }
        ::= { rcPortLacpEntry 3 }

rcPortLacpSlowPeriodicTime OBJECT-TYPE
        SYNTAX        Integer32 (10000..30000)
        MAX-ACCESS    read-write
        STATUS        current
        DESCRIPTION   "The number of miliseconds between periodic transmissions
                       using LONG Timeouts."
        DEFVAL        { 30000 }
        ::= { rcPortLacpEntry 4 }

rcPortLacpTimeoutScale OBJECT-TYPE
        SYNTAX         Integer32 (1..10)
        MAX-ACCESS    read-write
        STATUS        current
        DESCRIPTION   "Scalar value used to calculate timeout time from
                       periodic time. Timeout = PeriodicTime * TimeoutScale"
        DEFVAL        { 3 }
        ::= { rcPortLacpEntry 5 }

rcPortLacpAggrWaitTime OBJECT-TYPE
        SYNTAX        Integer32 (200..2000)
        MAX-ACCESS    read-write
        STATUS        current
        DESCRIPTION   "The number of mili seconds to delay aggregation to
                       allow multiple links to aggregate simultaneously."
        DEFVAL        { 2000 }
        ::= { rcPortLacpEntry 6 }

rcPortLacpFastPeriodicTimeOper OBJECT-TYPE
        SYNTAX        Integer32 (10..20000) 
        MAX-ACCESS    read-only
        STATUS        current
        DESCRIPTION   "The operating value of fast periodic timer on the port."
        ::= { rcPortLacpEntry 7 }

rcPortLacpSlowPeriodicTimeOper OBJECT-TYPE
        SYNTAX        Integer32 (10..30000) 
        MAX-ACCESS    read-only
        STATUS        current
        DESCRIPTION   "The operating value of slow periodic timer on the port."
        ::= { rcPortLacpEntry 8 }

rcPortLacpTimeoutScaleOper OBJECT-TYPE
        SYNTAX        Integer32 (1..10) 
        MAX-ACCESS    read-only
        STATUS        current
        DESCRIPTION   "The operating value of timeout scale on the port."
        ::= { rcPortLacpEntry 9 }

rcPortLacpAggrWaitTimeOper OBJECT-TYPE
        SYNTAX        Integer32 (10..2000) 
        MAX-ACCESS    read-only
        STATUS        current
        DESCRIPTION   "The operating value of aggreagate wait time on port."
        ::= { rcPortLacpEntry 10 }

rcPortVLacpTable OBJECT-TYPE
        SYNTAX        SEQUENCE OF RcPortVLacpEntry
        MAX-ACCESS    not-accessible
        STATUS        current
        DESCRIPTION   "Port Virtual LACP table"
        ::= { rcPort 5 }

rcPortVLacpEntry OBJECT-TYPE
        SYNTAX        RcPortVLacpEntry
        MAX-ACCESS    not-accessible
        STATUS        current
        DESCRIPTION   "Entry containing info. for a particular port"
        INDEX         { rcPortIndex }
        ::= { rcPortVLacpTable 1 }

RcPortVLacpEntry ::= SEQUENCE {
    rcPortVLacpAdminEnable                 TruthValue,
    rcPortVLacpOperEnable                  TruthValue,
    rcPortVLacpFastPeriodicTimer           Integer32,
    rcPortVLacpSlowPeriodicTimer           Integer32,
    rcPortVLacpTimeout                     INTEGER,
    rcPortVLacpTimeoutScale                Integer32,
    rcPortVLacpEtherType                   Integer32,
    rcPortVLacpEtherMacAddress             MacAddress,
    rcPortVLacpPortState                   INTEGER,
    rcPortVLacpDualHomingEnable            TruthValue,
    rcPortVlacpFlapDetectEnable            TruthValue,
    rcPortVlacpFlapFrequency               Integer32,
    rcPortVlacpFlapInterval                Integer32
    }

rcPortVLacpAdminEnable OBJECT-TYPE
        SYNTAX        TruthValue
        MAX-ACCESS    read-write
        STATUS        current
        DESCRIPTION   "Administratively enable/disable Virtual LACP on a port"
        DEFVAL        { false }
        ::= { rcPortVLacpEntry 1 }

rcPortVLacpOperEnable OBJECT-TYPE
        SYNTAX        TruthValue
        MAX-ACCESS    read-only
        STATUS        current
        DESCRIPTION   "Indicates if Virtual LACP is operationally enabled or
                       disabled on a port"
        ::= { rcPortVLacpEntry 2 }

rcPortVLacpFastPeriodicTimer OBJECT-TYPE
        SYNTAX        Integer32 (200..20000)
        MAX-ACCESS        read-write
        STATUS        current
        DESCRIPTION   "The number of miliseconds between periodic transmissions
                       using Short Timeouts"
        DEFVAL        { 250 }
        ::= { rcPortVLacpEntry 3 }

rcPortVLacpSlowPeriodicTimer OBJECT-TYPE
        SYNTAX        Integer32 (10000..30000)
        MAX-ACCESS    read-write
        STATUS        current
        DESCRIPTION   "The number of miliseconds between periodic transmissions
                       using LONG Timeouts."
        DEFVAL        { 30000 }
        ::= { rcPortVLacpEntry 4 }

rcPortVLacpTimeout     OBJECT-TYPE
        SYNTAX        INTEGER {
                         short(1),
                         long(2)
                      }
        MAX-ACCESS    read-write
        STATUS        current
        DESCRIPTION   "Timeout control value. Long or Short Timeout"
        ::= { rcPortVLacpEntry 5 }

rcPortVLacpTimeoutScale OBJECT-TYPE
        SYNTAX        Integer32 (1..10)
        MAX-ACCESS    read-write
        STATUS        current
        DESCRIPTION   "Scalar value used to calculate timeout time from
                       periodic time. Timeout = PeriodicTime * TimeoutScale"
        DEFVAL        { 3 }
        ::= { rcPortVLacpEntry 6 }

rcPortVLacpEtherType  OBJECT-TYPE
        SYNTAX        Integer32
        MAX-ACCESS    read-write
        STATUS        current
        DESCRIPTION   "VLACP Protocol Identification. The id value is
                       in Hex"
        DEFVAL        { 8103 }
        ::= { rcPortVLacpEntry 7 }

rcPortVLacpEtherMacAddress OBJECT-TYPE
        SYNTAX         MacAddress
        MAX-ACCESS     read-write
        STATUS         current
        DESCRIPTION    "Multicast Mac Address exclusively used for VLACPDU's"
        ::= { rcPortVLacpEntry 8 }

rcPortVLacpPortState OBJECT-TYPE
        SYNTAX         INTEGER {
                          up(1),
                          down(2)
                       }
        MAX-ACCESS     read-only
        STATUS         current
        DESCRIPTION    "Display the Vlacp Port State."
        ::= { rcPortVLacpEntry 9 }

rcPortVLacpDualHomingEnable OBJECT-TYPE
        SYNTAX        TruthValue
        MAX-ACCESS    read-write
        STATUS        current
        DESCRIPTION   "Enable/Disable Dual homing on Virtual LACP on a port"
        DEFVAL        { false }
        ::= { rcPortVLacpEntry 10 }

rcPortVlacpFlapDetectEnable OBJECT-TYPE
        SYNTAX         TruthValue
        MAX-ACCESS     read-write
        STATUS         current
        DESCRIPTION    "Administratively enable/disable VLACP flap detect on a port"
        DEFVAL         { false }
        ::= { rcPortVLacpEntry 11 }

rcPortVlacpFlapFrequency OBJECT-TYPE
       SYNTAX         Integer32 (1..9999)
        MAX-ACCESS     read-write
        STATUS         current
        DESCRIPTION    "The number of frequency for VLACP flap detect feature"
        DEFVAL         { 3 }
        ::= { rcPortVLacpEntry 12 }

rcPortVlacpFlapInterval OBJECT-TYPE
        SYNTAX         Integer32 (10..600)
        MAX-ACCESS     read-write
        STATUS         current
        DESCRIPTION    "The number of intevals for VLACP flap detect feature"
        DEFVAL         { 60 }
        ::= { rcPortVLacpEntry 13 }


-- Port Remote Mirroring Table

rcPortRemoteMirroringTable OBJECT-TYPE
        SYNTAX        SEQUENCE OF RcPortRemoteMirroringEntry
        MAX-ACCESS    not-accessible
        STATUS        current
        DESCRIPTION   "Port Remote Mirroring Table"
        ::= { rcPort 6 }

rcPortRemoteMirroringEntry OBJECT-TYPE
        SYNTAX        RcPortRemoteMirroringEntry
        MAX-ACCESS    not-accessible
        STATUS        current
        DESCRIPTION   "Entry containing remote mirroring info. for a
                       particular port"
        INDEX         { rcPortRemoteMirroringIndex }
        ::= { rcPortRemoteMirroringTable 1 }

RcPortRemoteMirroringEntry ::= SEQUENCE {
        rcPortRemoteMirroringIndex            InterfaceIndex,
        rcPortRemoteMirroringEnable           TruthValue,
        rcPortRemoteMirroringMode             INTEGER,
        rcPortRemoteMirroringSrcMac           MacAddress,
        rcPortRemoteMirroringDstMac           MacAddress,
        rcPortRemoteMirroringEtherType        Integer32,
        rcPortRemoteMirroringVlanIdListSize   Integer32,
        rcPortRemoteMirroringVlanIdList       OCTET STRING,
        rcPortRemoteMirroringRowStatus        RowStatus
        }


rcPortRemoteMirroringIndex OBJECT-TYPE
        SYNTAX          InterfaceIndex
        MAX-ACCESS      read-only
        STATUS          current
        DESCRIPTION     "An index value that uniquely identifies a port.
                         This value is similar to ifIndex in MIB2."
        ::= { rcPortRemoteMirroringEntry 1 }

rcPortRemoteMirroringEnable OBJECT-TYPE
        SYNTAX          TruthValue
        MAX-ACCESS      read-create
        STATUS          current
        DESCRIPTION     "To enable remote Mirroring for the port"
        DEFVAL          { false }
        ::= { rcPortRemoteMirroringEntry 2 }

rcPortRemoteMirroringMode OBJECT-TYPE
        SYNTAX          INTEGER {
                                source(1),
                                termination(2)
                        }
        MAX-ACCESS      read-create
        STATUS          current
        DESCRIPTION     "Mode in which remote mirroring is enabled"
        DEFVAL          { source }
        ::= { rcPortRemoteMirroringEntry 3 }

rcPortRemoteMirroringSrcMac OBJECT-TYPE
        SYNTAX          MacAddress
        MAX-ACCESS      read-create
        STATUS          current
        DESCRIPTION     "Source Mac of the remote mirrored packet.
                         Remote mirroring packet will be send with
                         this source mac address"
        ::= { rcPortRemoteMirroringEntry 4 }


rcPortRemoteMirroringDstMac OBJECT-TYPE
        SYNTAX          MacAddress
        MAX-ACCESS      read-create
        STATUS          current
        DESCRIPTION     "Destination Mac of the remote mirrored packet.
                         Packets will be bridged to this mac address.
                         Remote mirroring packet will be send to this
                         mac address"
        ::= { rcPortRemoteMirroringEntry 5 }

rcPortRemoteMirroringEtherType OBJECT-TYPE
        SYNTAX          Integer32 (0..65535)
        MAX-ACCESS      read-create
        STATUS          current
        DESCRIPTION     "Ethertype of the remote mirrored packet. Packets
                         will be send with this ethertype"
        DEFVAL          { '8103'h }
        ::= { rcPortRemoteMirroringEntry 6 }

rcPortRemoteMirroringVlanIdListSize OBJECT-TYPE
        SYNTAX          Integer32 (0..2000)
        MAX-ACCESS      read-only
        STATUS          current
        DESCRIPTION     "Used to indicate the number of VLAN IDs
                         that are assigned to this port."
        ::= { rcPortRemoteMirroringEntry 7 }

rcPortRemoteMirroringVlanIdList OBJECT-TYPE
        SYNTAX          OCTET STRING (SIZE(4096))
        MAX-ACCESS      read-create
        STATUS          current
        DESCRIPTION     "This field is used only if the port is assigned as
                         remote mirroring termination port. Represents zero
                         or more filter lists vlan in which the Destination
                         Mac address resides.  Each VLAN ID is stored as
                         two bytes in this array starting from offset zero.
                         Any unused bytes should be set to zero."
        ::= { rcPortRemoteMirroringEntry 8 }

rcPortRemoteMirroringRowStatus OBJECT-TYPE
        SYNTAX          RowStatus
        MAX-ACCESS      read-create
        STATUS          current
        DESCRIPTION     "RowStatus"
        ::= { rcPortRemoteMirroringEntry 9 }


-- Start of Vlacp session
rcPortVlacpSessionTable OBJECT-TYPE
          SYNTAX        SEQUENCE OF RcPortVlacpSessionEntry
          MAX-ACCESS    not-accessible
          STATUS        current
          DESCRIPTION   "A table used to maintain Vlacp session values."
         ::= { rcPort 7 }

rcPortVlacpSessionEntry OBJECT-TYPE
          SYNTAX        RcPortVlacpSessionEntry
          MAX-ACCESS    not-accessible
          STATUS        current
          DESCRIPTION   "Entry containing Vlacp Session information
                        regarding a particular port or mlt."
          INDEX         { rcPortVlacpSessionIfIndex,
                          rcPortVlacpSessionSesNumber }
          ::= { rcPortVlacpSessionTable 1 }

RcPortVlacpSessionEntry ::= SEQUENCE {
        rcPortVlacpSessionIfIndex              Integer32,
        rcPortVlacpSessionSesNumber            Integer32,
        rcPortVlacpSessionSrcMacAddress        MacAddress,
        rcPortVlacpSessionRxTimer              Integer32,
        rcPortVlacpSessionValidbit             INTEGER,
        rcPortVlacpSessionInPktCount           Integer32
        }

rcPortVlacpSessionIfIndex OBJECT-TYPE
          SYNTAX          Integer32 (0..2147483647)
          MAX-ACCESS      not-accessible
          STATUS          current
          DESCRIPTION     "IfIndex of the port or Mlt"
          ::= { rcPortVlacpSessionEntry 1 }

rcPortVlacpSessionSesNumber OBJECT-TYPE
          SYNTAX           Integer32 (0..2147483647)
          MAX-ACCESS       not-accessible
          STATUS           current
          DESCRIPTION      "Session number of an IfIndex"
          ::= { rcPortVlacpSessionEntry 2 }

rcPortVlacpSessionSrcMacAddress OBJECT-TYPE
          SYNTAX           MacAddress
          MAX-ACCESS       read-only
          STATUS           current
          DESCRIPTION      "Mac Address for the session"
          ::= { rcPortVlacpSessionEntry 3 }

rcPortVlacpSessionRxTimer OBJECT-TYPE
            SYNTAX          Integer32
            MAX-ACCESS      read-only
            STATUS          current
            DESCRIPTION     "The Rx timer for the session"
            ::= { rcPortVlacpSessionEntry 4 }

rcPortVlacpSessionValidbit OBJECT-TYPE
            SYNTAX          INTEGER
                            {
                               inValidSession(0),
                               validSession(1)
                            }
            MAX-ACCESS      read-only
            STATUS          current
            DESCRIPTION     "The valid bit for the session"
            ::= { rcPortVlacpSessionEntry 5 }

rcPortVlacpSessionInPktCount OBJECT-TYPE
            SYNTAX          Integer32
            MAX-ACCESS      read-only
            STATUS          current
            DESCRIPTION     "The In packet count for the session"
            ::= { rcPortVlacpSessionEntry 6 }

-- End of Vlacp session

-- Management port details

rcPortMgmtLinkTable OBJECT-TYPE
        SYNTAX        SEQUENCE OF RcPortMgmtLinkEntry
        MAX-ACCESS    not-accessible
        STATUS        current
        DESCRIPTION   "Port card mgmt port link table"
        ::= { rcPort 8 }

rcPortMgmtLinkEntry OBJECT-TYPE
        SYNTAX        RcPortMgmtLinkEntry
        MAX-ACCESS    not-accessible
        STATUS        current
        DESCRIPTION   "Entry containing info. for a particular mgmt port in I/O
                      card"
        INDEX         { rcPortMgmtLinkIndex }
        ::= { rcPortMgmtLinkTable 1 }

RcPortMgmtLinkEntry ::= SEQUENCE {
        rcPortMgmtLinkIndex                   InterfaceIndex,
        rcPortMgmtLinkDescr                   DisplayString,
        rcPortMgmtLinkOperStatus              INTEGER,
        rcPortMgmtLinkAutoNegotiate           TruthValue,
        rcPortMgmtLinkDuplex                  INTEGER,
        rcPortMgmtLinkSpeed                   INTEGER
        }

rcPortMgmtLinkIndex OBJECT-TYPE
        SYNTAX        InterfaceIndex
        MAX-ACCESS    read-only
        STATUS        current
        DESCRIPTION   "IfIndex of the port."
        ::= { rcPortMgmtLinkEntry 1 }

rcPortMgmtLinkDescr OBJECT-TYPE
        SYNTAX        DisplayString (SIZE (0..128))
        MAX-ACCESS    read-only
        STATUS        current
        DESCRIPTION   "Port description"
        ::= { rcPortMgmtLinkEntry 2 }

rcPortMgmtLinkOperStatus OBJECT-TYPE
        SYNTAX          INTEGER
                        {
                            up(1),
                            down(2),
                            unknown(3)
                        }
        MAX-ACCESS      read-only
        STATUS          current
        DESCRIPTION     "admin status of the mgmt port"
        ::= { rcPortMgmtLinkEntry 3 }

rcPortMgmtLinkAutoNegotiate OBJECT-TYPE
        SYNTAX          TruthValue
        MAX-ACCESS      read-only
        STATUS          current
        DESCRIPTION     "Auto-negotiation status of the port"
        ::= { rcPortMgmtLinkEntry 4 }

rcPortMgmtLinkDuplex OBJECT-TYPE
        SYNTAX          INTEGER
                        {
                            half(1),
                            full(2)
                        }
        MAX-ACCESS      read-only
        STATUS          current
        DESCRIPTION     "duplex setting for the port"
        ::= { rcPortMgmtLinkEntry 5 }

rcPortMgmtLinkSpeed OBJECT-TYPE
        SYNTAX          INTEGER
                        {
                            none(0),
                            mbps10(1),      -- 10Mb/s
                            mbps100(2),      -- 100Mb/s
                            mbps1000(3)     -- 1000Mb/s
                        }
        MAX-ACCESS      read-only
        STATUS          current
        DESCRIPTION     "speed setting for this port."
        ::= { rcPortMgmtLinkEntry 6 }

-- PORT FlushFdbTable

rcPortFlushFdbTable OBJECT-TYPE
       SYNTAX        SEQUENCE OF RcPortFlushFdbEntry
       MAX-ACCESS    not-accessible
       STATUS        current
       DESCRIPTION   "Port Flush Fdbtable"
        ::= { rcPort 9 }

rcPortFlushFdbEntry OBJECT-TYPE
        SYNTAX        RcPortFlushFdbEntry
        MAX-ACCESS    not-accessible
        STATUS        current
        DESCRIPTION   "port based deletion of mac addresses
                       learned or discarded on that port"
        INDEX         { rcPortIndex }
        ::= { rcPortFlushFdbTable 1 }

RcPortFlushFdbEntry ::= SEQUENCE {
        rcPortFlushFdbAddress                DisplayString,
        rcPortFlushFdbVlanId                 Integer32
        }

rcPortFlushFdbAddress OBJECT-TYPE
        SYNTAX          DisplayString (SIZE (17))
        MAX-ACCESS      read-write
        STATUS          current
        DESCRIPTION     "Mac Address to be deleted."
        ::= { rcPortFlushFdbEntry 1 }

rcPortFlushFdbVlanId OBJECT-TYPE
        SYNTAX      Integer32(1..4094)
        MAX-ACCESS  read-write
        STATUS      current
        DESCRIPTION  "vlan Id associated with the Mac Address"
        ::= { rcPortFlushFdbEntry 2 }

-- Port Flush Mac Table

rcPortFlushMacTable	OBJECT-TYPE
	SYNTAX		SEQUENCE OF RcPortFlushMacEntry
	MAX-ACCESS	not-accessible
	STATUS		current
	DESCRIPTION	"Flush MAC entry on a port."
	::= { rcPort 11 }

rcPortFlushMacEntry	OBJECT-TYPE
	SYNTAX		RcPortFlushMacEntry
	MAX-ACCESS	not-accessible
	STATUS		current
	DESCRIPTION	"Port mac flush table entry."
	INDEX		{ rcPortFlushMacPortNum }
	::= { rcPortFlushMacTable 1 }

RcPortFlushMacEntry ::=
	SEQUENCE
	{
		rcPortFlushMacPortNum	INTEGER,
		rcPortFlushMacAddr	OCTET STRING,
		rcPortFlushMacVlanId	INTEGER
	}

rcPortFlushMacPortNum	OBJECT-TYPE
        SYNTAX        INTEGER (1..2147483647)
        MAX-ACCESS    not-accessible
        STATUS        current
        DESCRIPTION   "Port number where the mac record exists."
        ::= { rcPortFlushMacEntry 1 }

rcPortFlushMacAddr	OBJECT-TYPE
        SYNTAX        OCTET STRING (SIZE(17))
        MAX-ACCESS    read-write
        STATUS        current
        DESCRIPTION   "Mac Address that needs to be removed."
        ::= { rcPortFlushMacEntry 2 }

rcPortFlushMacVlanId OBJECT-TYPE
        SYNTAX        INTEGER (1..4094)
        MAX-ACCESS    read-write
        STATUS        current
        DESCRIPTION   "Vlan Id associated with the Mac Address."
        ::= { rcPortFlushMacEntry 3 }

------------------------------------------------------------------------------
-- LLDP-MED - Local Device Information
------------------------------------------------------------------------------
---
--- rcLldpXMedLocMediaPolicyTable: Local Media Policy
---                        Information Table
---
---
rcLldpXMedLocMediaPolicyTable OBJECT-TYPE
    SYNTAX      SEQUENCE OF RcLldpXMedLocMediaPolicyEntry
    MAX-ACCESS  not-accessible
    STATUS      current
    DESCRIPTION
            "This table contains one row per policy type per port
             of media policy information (as a part of the MED
             organizational extension) on the local system known
             to this agent."
    ::= { rcPort 12 }

rcLldpXMedLocMediaPolicyEntry OBJECT-TYPE
    SYNTAX      RcLldpXMedLocMediaPolicyEntry
    MAX-ACCESS  not-accessible
    STATUS      current
    DESCRIPTION
            "Information about a particular policy on a specific
             port component."
    INDEX   { rcLldpXMedLocMediaPolicyPortNum, rcLldpXMedLocMediaPolicyAppType }
    ::= { rcLldpXMedLocMediaPolicyTable 1 }

RcLldpXMedLocMediaPolicyEntry ::=
              SEQUENCE {
                  rcLldpXMedLocMediaPolicyPortNum        InterfaceIndex,
                  rcLldpXMedLocMediaPolicyAppType        PolicyAppType,
                  rcLldpXMedLocMediaPolicyVlanID         Integer32,
                  rcLldpXMedLocMediaPolicyPriority       Integer32,
                  rcLldpXMedLocMediaPolicyDscp           Integer32,
                  rcLldpXMedLocMediaPolicyUnknown        TruthValue,
                  rcLldpXMedLocMediaPolicyTagged         TruthValue,
                  rcLldpXMedLocMediaPolicyRowStatus      RowStatus
}

rcLldpXMedLocMediaPolicyPortNum OBJECT-TYPE
    SYNTAX      InterfaceIndex
    MAX-ACCESS  not-accessible
    STATUS      current
    DESCRIPTION
            "."
    ::= { rcLldpXMedLocMediaPolicyEntry 1 }

rcLldpXMedLocMediaPolicyAppType OBJECT-TYPE
    SYNTAX      PolicyAppType
    MAX-ACCESS  not-accessible
    STATUS      current
    DESCRIPTION
            "The media type that defines the primary function of the
             application for the policy advertised by an endpoint."
    REFERENCE
            "ANSI/TIA-1057, Section 10.2.3.1"
    ::= { rcLldpXMedLocMediaPolicyEntry 2 }

rcLldpXMedLocMediaPolicyVlanID  OBJECT-TYPE
    SYNTAX      Integer32 (0|1..4094|4095)

    MAX-ACCESS  read-create
    STATUS      current
    DESCRIPTION
            "An extension of the VLAN Identifier for the port,
             as defined in IEEE 802.1P-1998.


             A value of 1 through 4094 is used to define a valid PVID.

             A value of 0 shall be used if the device is using priority tagged
             frames, meaning that only the 802.1p priority level is significant
             and the default VID of the ingress port is being used instead.

             A value of 4095 is reserved for implementation use."
    REFERENCE
            " ANSI/TIA-1057, Section 10.2.3.5"
    ::= { rcLldpXMedLocMediaPolicyEntry 3 }

rcLldpXMedLocMediaPolicyPriority  OBJECT-TYPE
    SYNTAX      Integer32 (0..7)
    MAX-ACCESS  read-create
    STATUS      current
    DESCRIPTION
            "This object contains the value of the 802.1p priority
            which is associated with the given port on the
            local system."
    REFERENCE
            " ANSI/TIA-1057, Section 10.2.3.6 "
    ::= { rcLldpXMedLocMediaPolicyEntry 4 }

rcLldpXMedLocMediaPolicyDscp  OBJECT-TYPE
    SYNTAX      Integer32(0..63)
    MAX-ACCESS  read-create
    STATUS      current
    DESCRIPTION
            "This object contains the value of the Differentiated Service
            Code Point (DSCP) as defined in IETF RFC 2474 and RFC 2475
            which is associated with the given port on the local system."
    REFERENCE
            " ANSI/TIA-1057, Section 10.2.3.7"
    ::= { rcLldpXMedLocMediaPolicyEntry 5 }

rcLldpXMedLocMediaPolicyUnknown  OBJECT-TYPE
    SYNTAX      TruthValue
    MAX-ACCESS  read-create
    STATUS      current
    DESCRIPTION
            "A value of 'true' indicates that the
             network policy for the specified application type is
             currently unknown.  In this case, the VLAN ID, the
             layer 2 priority and the DSCP value fields are ignored.
             A value of 'false' indicates that this network policy
             is defined  "
    REFERENCE
            " ANSI/TIA-1057, Section 10.2.3.2"
    ::= { rcLldpXMedLocMediaPolicyEntry 6 }

rcLldpXMedLocMediaPolicyTagged  OBJECT-TYPE
    SYNTAX      TruthValue
    MAX-ACCESS  read-create
    STATUS      current
    DESCRIPTION
            "A value of 'true' indicates that the application is using a

             tagged VLAN.
             A value of 'false' indicates that for the specific application
             the device either is using an untagged VLAN or does not
             support port based VLAN operation.  In this case, both the
             VLAN ID and the Layer 2 priority fields are ignored and
             only the DSCP value has relevance "
    REFERENCE
            " ANSI/TIA-1057, Section 10.2.3.3"
    ::= { rcLldpXMedLocMediaPolicyEntry 7 }

rcLldpXMedLocMediaPolicyRowStatus OBJECT-TYPE
    SYNTAX      RowStatus
    MAX-ACCESS  read-create
    STATUS      current
    DESCRIPTION
            "Used to create/delete entries."

    ::= { rcLldpXMedLocMediaPolicyEntry 8 }
    
-- ===========================================================================
-- Port Lock Group
-- ===========================================================================

rcPortRemotePortShutdownTable OBJECT-TYPE
    SYNTAX SEQUENCE OF RcPortRemotePortShutdownEntry
    MAX-ACCESS not-accessible
    STATUS current
    DESCRIPTION
        "A list of RemotePortShutdown port info."
    ::= { rcPort 10 }

rcPortRemotePortShutdownEntry OBJECT-TYPE
    SYNTAX RcPortRemotePortShutdownEntry
    MAX-ACCESS not-accessible
    STATUS current
    DESCRIPTION
        "A RemotePortShutdown table entry."
    INDEX { rcPortRemotePortShutdownIfIndex }
    ::= { rcPortRemotePortShutdownTable 1 }

RcPortRemotePortShutdownEntry ::=
    SEQUENCE {
        rcPortRemotePortShutdownIfIndex          InterfaceIndex,
        rcPortRemotePortShutdownEnabled          TruthValue,
        rcPortRemotePortShutdownHoldTimer        Integer32,
        rcPortRemotePortShutdownStatus           INTEGER,
        rcPortRemotePortShutdownLocalMacAddress  MacAddress,
        rcPortRemotePortShutdownRemoteMacAddress MacAddress
    }

rcPortRemotePortShutdownIfIndex OBJECT-TYPE
    SYNTAX      InterfaceIndex
    MAX-ACCESS  not-accessible
    STATUS      current
    DESCRIPTION
        "The ifIndex value for a port."
    ::= { rcPortRemotePortShutdownEntry 1 }

rcPortRemotePortShutdownEnabled OBJECT-TYPE
    SYNTAX      TruthValue
    MAX-ACCESS  read-write
    STATUS      current
    DESCRIPTION
        "This object controls whether the Remote-Port-Shutdown feature is
        enabled or disabled on a port."
    DEFVAL      { false }
    ::= { rcPortRemotePortShutdownEntry 2 }

rcPortRemotePortShutdownHoldTimer OBJECT-TYPE
    SYNTAX      Integer32 (0..10)
    UNITS       "seconds"
    MAX-ACCESS  read-write
    STATUS      current
    DESCRIPTION
        "Indicates the time period after a port has been shutdown during which
        it will remain down, regardless of any CCMs received during that time
        period."
    DEFVAL      { 3 }
    ::= { rcPortRemotePortShutdownEntry 3 }

rcPortRemotePortShutdownStatus OBJECT-TYPE
    SYNTAX      INTEGER {
                  up (1),
                  down (2)
               }
    MAX-ACCESS  read-only
    STATUS      current
    DESCRIPTION
        "This object indicates whether a port is shutdown by the remote port
        shutdown feature."
    ::= { rcPortRemotePortShutdownEntry 4 }

rcPortRemotePortShutdownLocalMacAddress OBJECT-TYPE
    SYNTAX      MacAddress
    MAX-ACCESS  read-only
    STATUS      current
    DESCRIPTION
        "Local MAC address."
    ::= { rcPortRemotePortShutdownEntry 5 }

rcPortRemotePortShutdownRemoteMacAddress OBJECT-TYPE
    SYNTAX      MacAddress
    MAX-ACCESS  read-only
    STATUS      current
    DESCRIPTION
        "Remote MAC address."
    ::= { rcPortRemotePortShutdownEntry 6 }

-- Port Lock Group

rcPortLock OBJECT IDENTIFIER ::= { rcChassis 11 }

rcPortLockEnable OBJECT-TYPE
        SYNTAX          TruthValue
        MAX-ACCESS              read-write
        STATUS          current
        DESCRIPTION     "Indicate whether the port lock feature is enabled."
        DEFVAL          { false }
        ::= { rcPortLock 1 }

rcPortLockLockedPorts OBJECT-TYPE
        SYNTAX          PortSet
        MAX-ACCESS              read-write
        STATUS          current
        DESCRIPTION     "The set of ports that are administratively locked.
                        Locked ports cannot be modified in anyway until the
                        port is unlocked first."
        ::= { rcPortLock 2 }


-- Test Group

rcTestExtTable OBJECT-TYPE
        SYNTAX        SEQUENCE OF RcTestEntry
        MAX-ACCESS    not-accessible
        STATUS        current
        DESCRIPTION   "Test extension table.  This table augments the
                      standard ifTestTable table in RFC1573."
        ::= { rcTest 1 }
 
rcTestEntry OBJECT-TYPE
        SYNTAX        RcTestEntry
        MAX-ACCESS    not-accessible
        STATUS        current    
        DESCRIPTION   "Proprietary test variables."
        INDEX         { rcTestExtIfIndex }
        ::= { rcTestExtTable 1 }
 
RcTestEntry ::=
        SEQUENCE {
                rcTestExtIfIndex InterfaceIndex,
                rcTestExtPassCount Integer32,  
                rcTestExtFailCount Integer32
        }
 
rcTestExtIfIndex OBJECT-TYPE
        SYNTAX        InterfaceIndex
        MAX-ACCESS    read-only
        STATUS        current
        DESCRIPTION   "The index value which uniquely identifies the
                      interface to which this entry is applicable.
                      The interface identified by a particular value
                      of this index is the same interface as
                      identified by the same value of ifIndex."
        ::= { rcTestEntry 1 }

rcTestExtPassCount OBJECT-TYPE
	SYNTAX	      Integer32
	MAX-ACCESS	  read-only
	STATUS	      current
	DESCRIPTION   "The number of iterations of the test case that
		      completed successfully."
	::= { rcTestEntry 2}

rcTestExtFailCount OBJECT-TYPE
        SYNTAX        Integer32
        MAX-ACCESS    read-only
        STATUS        current
        DESCRIPTION   "The number of iterations of the test case that
                      failed."
        ::= { rcTestEntry 3}


rcTestTypes		OBJECT IDENTIFIER	::= { rcTest 2}
rcTestTypesFabric	OBJECT IDENTIFIER	::= { rcTestTypes 1 }
rcTestTypesArTable	OBJECT IDENTIFIER	::= { rcTestTypes 2 }
rcTestTypesExtLoopBack	OBJECT IDENTIFIER	::= { rcTestTypes 3 }


rcTestCodes		OBJECT IDENTIFIER	::= { rcTest 3 }
rcTestCodesNoReceive	OBJECT IDENTIFIER	::= { rcTestCodes 1 }
rcTestCodesBadSeq	OBJECT IDENTIFIER	::= { rcTestCodes 2 }
rcTestCodesBadLen	OBJECT IDENTIFIER	::= { rcTestCodes 3 }
rcTestCodesBadData	OBJECT IDENTIFIER	::= { rcTestCodes 4 }


-- Statistics

rcStatTable OBJECT-TYPE
        SYNTAX        SEQUENCE OF RcStatEntry
        MAX-ACCESS    not-accessible
        STATUS        current
        DESCRIPTION   "A table used to store port statistics."
        ::= { rcStat 1 }
 
rcStatEntry OBJECT-TYPE
        SYNTAX        RcStatEntry
        MAX-ACCESS    not-accessible
        STATUS        current
        DESCRIPTION   "interface counters"
        INDEX         { rcStatPortIndex }
        ::= { rcStatTable 1 }
 
RcStatEntry ::= SEQUENCE {
                rcStatPortIndex            	InterfaceIndex,
                rcStatFrameTooShorts       	Counter32,
 		rcStatBridgeInUnicastFrames	Counter32,
 		rcStatBridgeInMulticastFrames	Counter32,
 		rcStatBridgeInBroadcastFrames	Counter32,
 		rcStatBridgeInDiscards		Counter32,
 		rcStatBridgeOutUnicastFrames	Counter32,
 		rcStatBridgeOutMulticastFrames	Counter32,
 		rcStatBridgeOutBroadcastFrames	Counter32,
 		rcStatRouteInUnicastFrames	Counter32,
 		rcStatRouteInMulticastFrames	Counter32,
 		rcStatRouteInDiscards		Counter32,
 		rcStatRouteOutUnicastFrames	Counter32,
 		rcStatRouteOutMulticastFrames 	Counter32,
		rcStatStgForwardTransitions     Counter32,
		rcStatStgInConfigBpdus          Counter32,
		rcStatStgInTcnBpdus             Counter32,
		rcStatStgInBadBpdus             Counter32,
		rcStatStgOutConfigBpdus         Counter32,
		rcStatStgOutTcnBpdus            Counter32,
		rcStatBridgeOutFrames           Counter32,
		rcStatPbtUnknownDropCount	Counter64,
                rcStatCtrlPktRtLimitTotalCnt    Counter64, 
		rcStatCtrlPktRtLimitDropCnt     Counter64,
                rcStatPolicerTotalBytes         Counter64,
                rcStatPolicerTotalPkts          Counter64,
                rcStatPolicerGreenBytes         Counter64,
                rcStatPolicerYellowBytes        Counter64,
                rcStatPolicerRedBytes           Counter64
        }
 
rcStatPortIndex OBJECT-TYPE
        SYNTAX        InterfaceIndex
        MAX-ACCESS    read-only
        STATUS        current
        DESCRIPTION   "An index value that uniquely identifies a port.
                      This value is similar to ifIndex in MIB2."
        ::= { rcStatEntry 1 }
 
rcStatFrameTooShorts OBJECT-TYPE
        SYNTAX        Counter32
        MAX-ACCESS    read-only
        STATUS        current
        DESCRIPTION   "The total number of frames that are too short 
                      that were encountered on this interface."
        ::= { rcStatEntry 2 }

rcStatBridgeInUnicastFrames OBJECT-TYPE
        SYNTAX        Counter32
        MAX-ACCESS    read-only
        STATUS        current
        DESCRIPTION   "The total number of incoming unicast frames that 
		      were bridged."
        ::= { rcStatEntry 3 }

rcStatBridgeInMulticastFrames OBJECT-TYPE 
        SYNTAX        Counter32 
        MAX-ACCESS    read-only
        STATUS        current 
        DESCRIPTION   "The total number of incoming multicast frames that 
                      were bridged."
        ::= { rcStatEntry 4 }

rcStatBridgeInBroadcastFrames OBJECT-TYPE 
        SYNTAX        Counter32 
        MAX-ACCESS    read-only
        STATUS        current 
        DESCRIPTION   "The total number of incoming broadcast frames that 
                      were bridged."
        ::= { rcStatEntry 5 }

rcStatBridgeInDiscards OBJECT-TYPE 
        SYNTAX        Counter32 
        MAX-ACCESS    read-only
        STATUS        current 
        DESCRIPTION   "The total number of frames that were discarded by
		      the bridging entity."
        ::= { rcStatEntry 6 }

rcStatBridgeOutUnicastFrames OBJECT-TYPE 
        SYNTAX        Counter32 
        MAX-ACCESS    read-only
        STATUS        current 
        DESCRIPTION   "The total number of outgoing unicast frames that 
                      were bridged."
        ::= { rcStatEntry 7 }

rcStatBridgeOutMulticastFrames OBJECT-TYPE 
        SYNTAX        Counter32 
        MAX-ACCESS    read-only
        STATUS        current 
        DESCRIPTION   "The total number of outgoing multicast frames that 
                      were bridged."
        ::= { rcStatEntry 8 }

rcStatBridgeOutBroadcastFrames OBJECT-TYPE 
        SYNTAX        Counter32 
        MAX-ACCESS    read-only
        STATUS        current 
        DESCRIPTION   "The total number of outgoing broadcast frames that 
                      were bridged."
        ::= { rcStatEntry 9 }

rcStatRouteInUnicastFrames OBJECT-TYPE 
        SYNTAX        Counter32 
        MAX-ACCESS    read-only
        STATUS        current 
        DESCRIPTION   "The total number of incoming unicast frames that
                      were routed."
        ::= { rcStatEntry 10 }

rcStatRouteInMulticastFrames OBJECT-TYPE 
        SYNTAX        Counter32 
        MAX-ACCESS    read-only
        STATUS        current 
        DESCRIPTION   "The total number of incoming multicast frames that
                      were routed."
        ::= { rcStatEntry 11 }

rcStatRouteInDiscards OBJECT-TYPE 
        SYNTAX        Counter32 
        MAX-ACCESS    read-only
        STATUS        current 
        DESCRIPTION   "The total number of frames that were discarded by
		      the routing entity."
        ::= { rcStatEntry 12 }

rcStatRouteOutUnicastFrames OBJECT-TYPE 
        SYNTAX        Counter32 
        MAX-ACCESS    read-only
        STATUS        current 
        DESCRIPTION   "The total number of outgoing unicast frames that
                      were routed."
        ::= { rcStatEntry 13 }

rcStatRouteOutMulticastFrames OBJECT-TYPE 
        SYNTAX        Counter32 
        MAX-ACCESS    read-only
        STATUS        current 
        DESCRIPTION   "The total number of outgoing multicast frames that
                      were routed."
        ::= { rcStatEntry 14 }

rcStatStgForwardTransitions OBJECT-TYPE 
        SYNTAX        Counter32 
        MAX-ACCESS    read-only
        STATUS        current 
        DESCRIPTION   "The number of times this port has transitioned
                      from the Learning state to the Forwarding state."
        ::= { rcStatEntry 15 }

rcStatStgInConfigBpdus OBJECT-TYPE 
        SYNTAX        Counter32 
        MAX-ACCESS    read-only
        STATUS        current 
        DESCRIPTION   "Received Config BPDUs"
        ::= { rcStatEntry 16 }

rcStatStgInTcnBpdus OBJECT-TYPE 
        SYNTAX        Counter32 
        MAX-ACCESS    read-only
        STATUS        current 
        DESCRIPTION   "Received TCN BPDUs"
        ::= { rcStatEntry 17 }

rcStatStgInBadBpdus OBJECT-TYPE 
        SYNTAX        Counter32 
        MAX-ACCESS    read-only
        STATUS        current 
        DESCRIPTION   "Received bad BPDUs"
        ::= { rcStatEntry 18 }

rcStatStgOutConfigBpdus OBJECT-TYPE 
        SYNTAX        Counter32 
        MAX-ACCESS    read-only
        STATUS        current 
        DESCRIPTION   "Transmitted config BPDUs"
        ::= { rcStatEntry 19 }

rcStatStgOutTcnBpdus OBJECT-TYPE 
        SYNTAX        Counter32 
        MAX-ACCESS    read-only
        STATUS        current 
        DESCRIPTION   "Transmitted TCN BPDUs"
        ::= { rcStatEntry 20 }

rcStatBridgeOutFrames OBJECT-TYPE 
        SYNTAX        Counter32 
        MAX-ACCESS    read-only
        STATUS        current 
        DESCRIPTION     "Used by the Accelar 8000 product family to account
                        for all transmitted bridge unicast, broadcast, and
                        multicast packets.  The individual counters are not
                        supported."
        ::= { rcStatEntry 21 }

rcStatPbtUnknownDropCount OBJECT-TYPE
        SYNTAX        Counter64
        MAX-ACCESS    read-only
        STATUS        current
        DESCRIPTION   "Count of PBT packets dropped due to unknown
		       destination MAC"
        ::= { rcStatEntry 22 }

rcStatCtrlPktRtLimitTotalCnt OBJECT-TYPE
        SYNTAX        Counter64
        MAX-ACCESS    read-only
        STATUS        current
        DESCRIPTION   "Total count of control packets that is passed for rate limiting"
        ::= { rcStatEntry 23 }  

rcStatCtrlPktRtLimitDropCnt  OBJECT-TYPE
        SYNTAX        Counter64
        MAX-ACCESS    read-only
        STATUS        current
        DESCRIPTION   "Count of control packets dropped after rate limiting"
        ::= { rcStatEntry 24 }

rcStatPolicerTotalBytes OBJECT-TYPE
        SYNTAX        Counter64
        MAX-ACCESS    read-only
        STATUS        current
        DESCRIPTION   "The total number of bytes received on the
                       interface."
        ::= { rcStatEntry 25 }

rcStatPolicerTotalPkts OBJECT-TYPE
        SYNTAX        Counter64
        MAX-ACCESS    read-only
        STATUS        current
        DESCRIPTION   "The total number of packets received on the
                       interface."
        ::= { rcStatEntry 26 }

rcStatPolicerGreenBytes OBJECT-TYPE
        SYNTAX        Counter64
        MAX-ACCESS    read-only
        STATUS        current
        DESCRIPTION   "The total number of bytes received on the
                       interface that were below the committed rate."
        ::= { rcStatEntry 27 }

rcStatPolicerYellowBytes OBJECT-TYPE
        SYNTAX        Counter64
        MAX-ACCESS    read-only
        STATUS        current
        DESCRIPTION   "The total number of bytes received on the
                       interface that were above the committed rate
                       but below the peak rate."
        ::= { rcStatEntry 28 }

rcStatPolicerRedBytes OBJECT-TYPE
        SYNTAX        Counter64
        MAX-ACCESS    read-only
        STATUS        current
        DESCRIPTION   "The total number of bytes received on the
                       interface that were above the peak rate."
        ::= { rcStatEntry 29 }

--
--  Lossless Ethernet Port Table

rcPortLosslessEnetTable OBJECT-TYPE
        SYNTAX        SEQUENCE OF RcPortLosslessEnetEntry
        MAX-ACCESS    not-accessible
        STATUS        current
        DESCRIPTION   "Port Lossless Ethernet Table"
        ::= { rcPort 13 }

rcPortLosslessEnetEntry OBJECT-TYPE
        SYNTAX        RcPortLosslessEnetEntry
        MAX-ACCESS    not-accessible
        STATUS        current
        DESCRIPTION   "Entry containing lossless Ethernet information
                       for a particular port."
        INDEX         { rcPortLosslessEnetIndex }
        ::= { rcPortLosslessEnetTable 1 }

RcPortLosslessEnetEntry ::= SEQUENCE {
          rcPortLosslessEnetIndex        InterfaceIndex,
          rcPortLosslessEnetConfigured   TruthValue,
          rcPortLosslessEnetPauseType    INTEGER,
          rcPortLosslessEnetPfcBandwidth Integer32
        }

rcPortLosslessEnetIndex OBJECT-TYPE
        SYNTAX          InterfaceIndex
        MAX-ACCESS      not-accessible 
        STATUS          current
        DESCRIPTION     "An index value that uniquely identifies a port.
                         This value is similar to ifIndex in MIB2.
                         Lossless Ethernet will be limited to 10Gig
                         ports."
        ::= { rcPortLosslessEnetEntry 1 }

rcPortLosslessEnetConfigured OBJECT-TYPE
        SYNTAX          TruthValue
        MAX-ACCESS      read-write
        STATUS          current
        DESCRIPTION     "To enable lossless mode for the port"
        DEFVAL          { false }
        ::= { rcPortLosslessEnetEntry 2 }

rcPortLosslessEnetPauseType OBJECT-TYPE
        SYNTAX          INTEGER {
                                fc(1),
                                pfc(2)
                        }
        MAX-ACCESS      read-write
        STATUS          current
        DESCRIPTION     "Pause frame type.  fc - Pause,
                         pfc - priority-based flow control."
        DEFVAL          { fc }
        ::= { rcPortLosslessEnetEntry 3 }

rcPortLosslessEnetPfcBandwidth OBJECT-TYPE
        SYNTAX          Integer32(1..8)
        MAX-ACCESS      read-write
        STATUS          current
        DESCRIPTION     "Guaranteed bandwidth in Gbps when
                         rcPortLosslessEnetPauseType is set to pfc(2)."
        DEFVAL          { 5 }
        ::= { rcPortLosslessEnetEntry 4 }


END
